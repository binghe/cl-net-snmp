--
-- SNMPv2-CONF.mib
--
SNMPv2-CONF DEFINITIONS ::= BEGIN

-- OBJECT-GROUP predefined in mcompile.exe
-- NOTIFICATION-GROUP predefined in mcompile.exe
-- MODULE-COMPLIANCE predefined in mcompile.exe
-- AGENT-CAPABILITIES predefined in mcompile.exe

END
