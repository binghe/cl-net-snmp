-- *****************************************************************************
--                     HP NetServer Event Log Information 
--          Management Information Base for SNMP Network Management
--
--  Copyright 1995 Hewlett-Packard Company
--  All Rights Reserved.
--
--  The information in this document is subject to change without notice. 
--  The HP enterprise number is 11.
--  The ASN.1 prefix to, and including the HP Enterprise is: 1.3.6.1.4.1.11
--
--  File revision: 2.4
--
-- ****************************************************************************
-- Summary of HP NSA Event Log Information MIB
-- ****************************************************************************
-- hp  (1.3.6.1.4.1.11)
--    nm     (hp.2)
--      hpnsa      (nm.23)
--         hpnsaEventLog Group     (hpnsa.19) 
--              hpnsaEventLogRev Group         (hpnsa.19.1)
--                   hpnsaEventLogMibRevMajor        (hpnsa.19.1.1)
--                   hpnsaEventLogMibRevMinor        (hpnsa.19.1.2)
--
--              hpnsaEventLogAgentInfo Group   (hpnsa.19.2)
--                   hpnsaEventLogAgentTable         (hpnsa.19.2.1)
--                        hpnsaEventLogAgentEntry         (hpnsa.19.2.1.1)
--                             hpnsaEventLogAgentIndex        (hpnsa.19.2.1.1.1)
--                             hpnsaEventLogAgentName         (hpnsa.19.2.1.1.2)
--                             hpnsaEventLogAgentVersion      (hpnsa.19.2.1.1.3)
--                             hpnsaEventLogAgentDate         (hpnsa.19.2.1.1.4)
--                             
--              hpnsaEventAgentCfgInfo Group   (hpnsa.19.3)
--                   hpnsaEventCfgTable             (hpnsa.19.3.1)
--                        hpnsaEventCfgTableEntry        (hpnsa.19.3.1.1)
--                             hpnsaEventLogRecType         (hpnsa.19.3.1.1.1)
--                             hpnsaEventLogRecTrapEnable   (hpnsa.19.3.1.1.2)
--
--              hpnsaEventLogPresenceId Group  (hpnsa.19.4)
--                   hpnsaEccPresent                (hpnsa.19.4.1)
--                   hpnsaPostPresent               (hpnsa.19.4.2)
--                   hpnsaTempVoltagePresent        (hpnsa.19.4.3)
--                   hpnsaASRPresent                (hpnsa.19.4.4)
--                   hpnsaNMIPresent                (hpnsa.19.4.5)
--      
--              hpnsaEventLogStatistics Group   (hpnsa.19.5)
--                   hpnsaEventLogPercentFull       (hpnsa.19.5.1)
--                   hpnsaEventLogLastErasedDate    (hpnsa.19.5.2)
--                   hpnsaEventLogErasures          (hpnsa.19.5.3) 
--                   hpnsaEventLogEraseLog          (hpnsa.19.5.4) 
--                   hpnsaEventLogTable             (hpnsa.19.5.5)
--                        hpnsaEventLogTableEntry        (hpnsa.19.5.5.1)
--                             hpnsaEventLogTableIndex        (hpnsa.19.5.5.1.1)
--                             hpnsaEventLogEntryDate         (hpnsa.19.5.5.1.2)
--                             hpnsaEventLogEntryDescr        (hpnsa.19.5.5.1.3)  
--                             hpnsaEventLogEntryTrapID       (hpnsa.19.5.5.1.4)  
--                             hpnsaEventLogEntryVB1          (hpnsa.19.5.5.1.5)  
--                             hpnsaEventLogEntryVB2          (hpnsa.19.5.5.1.6)  
--                             hpnsaEventLogEntryVB3          (hpnsa.19.5.5.1.7)  
--                             hpnsaEventLogEntryVB4          (hpnsa.19.5.5.1.8)  
--                             hpnsaEventLogEntryVB5          (hpnsa.19.5.5.1.9)  
--                             hpnsaEventLogEntryVB6          (hpnsa.19.5.5.1.10)  
--                             hpnsaEventLogEntryVB7          (hpnsa.19.5.5.1.11)  
--                             hpnsaEventLogEntryVB8          (hpnsa.19.5.5.1.12)
--                             hpnsaEventLogEntryAdvisory     (hpnsa.19.5.5.1.13)
--                             hpnsaEventLogEntryReportEntity (hpnsa.19.5.5.1.14)  
--		     	       hpnsaEventLogEntrySeverity     (hpnsa.19.5.5.1.15)
--			       hpnsaEventLogEntryStatus	      (hpnsa.19.5.5.1.16)
--			       hpnsaEventLogEntryInfo	      (hpnsa.19.5.5.1.17)
--			       hpnsaEventLogEntryUpdateTime   (hpnsa.19.5.5.1.18)
--                   hpnsaEventLogNumberOfEvents    (hpnsa.19.5.6) 
--                   hpnsaEventLogAggregationStatus (hpnsa.19.5.7) 
--                   hpnsaEventLogLocalTable        (hpnsa.19.5.8)
--                        hpnsaEventLogLocalTableEntry        (hpnsa.19.5.8.1)
--                             hpnsaEventLogLocalTableIndex        (hpnsa.19.5.8.1.1)
--                             hpnsaEventLogLocalEntryDate         (hpnsa.19.5.8.1.2)
--                             hpnsaEventLogLocalEntryDescr        (hpnsa.19.5.8.1.3)  
--                             hpnsaEventLogLocalEntryTrapID       (hpnsa.19.5.8.1.4)  
--                             hpnsaEventLogLocalEntryVB1          (hpnsa.19.5.8.1.5)  
--                             hpnsaEventLogLocalEntryVB2          (hpnsa.19.5.8.1.6)  
--                             hpnsaEventLogLocalEntryVB3          (hpnsa.19.5.8.1.7)  
--                             hpnsaEventLogLocalEntryVB4          (hpnsa.19.5.8.1.8)  
--                             hpnsaEventLogLocalEntryVB5          (hpnsa.19.5.8.1.9)  
--                             hpnsaEventLogLocalEntryVB6          (hpnsa.19.5.8.1.10)  
--                             hpnsaEventLogLocalEntryVB7          (hpnsa.19.5.8.1.11)  
--                             hpnsaEventLogLocalEntryVB8          (hpnsa.19.5.8.1.12)
--                             hpnsaEventLogLocalEntryAdvisory     (hpnsa.19.5.8.1.13)
--                             hpnsaEventLogLocalEntryReportEntity (hpnsa.19.5.8.1.14)  
--		     	       hpnsaEventLogLocalEntrySeverity     (hpnsa.19.5.8.1.15)
--			       hpnsaEventLogLocalEntryStatus	   (hpnsa.19.5.8.1.16)
--			       hpnsaEventLogLocalEntryInfo	   (hpnsa.19.5.8.1.17)
--			       hpnsaEventLogLocalEntryUpdateTime   (hpnsa.19.5.8.1.18)
--                   hpnsaEventLogNumOfLocalEvents  (hpnsa.19.5.9) 
--              
--
-- Note : Objects within the hpnsaEventLogPresenceId group are somewhat dynamic - 
--        some will not be present in the MIB tree if the associated service is 
--        not supported or the respective errors are not being logged on the 
--        server. Moreover, the list of presence objects in that group will be 
--        constantly expanding as new types of errors start being logged in the 
--        hardware logging area. At any given time the event log agent will 
--        support only those objects that it needs to, based on the information 
--        it reads from the configuration file that resides on the server.
--
--
-- ****************************************************************************

HPNSAEVENT-MIB DEFINITIONS ::= BEGIN

    IMPORTS
	enterprises    FROM RFC1155-SMI
	Counter        FROM RFC1155-SMI
	DisplayString  FROM RFC1213-MIB
	OBJECT-TYPE    FROM RFC-1212;
--
    hp                      OBJECT IDENTIFIER ::= { enterprises 11 }
    nm                      OBJECT IDENTIFIER ::= { hp 2 }
    hpnsa                   OBJECT IDENTIFIER ::= { nm 23 }  
    hpnsaEventLog           OBJECT IDENTIFIER ::= { hpnsa 19 }
    hpnsaEventLogRev        OBJECT IDENTIFIER ::= { hpnsaEventLog 1 }
    hpnsaEventLogAgentInfo  OBJECT IDENTIFIER ::= { hpnsaEventLog 2 }
    hpnsaEventAgentCfgInfo  OBJECT IDENTIFIER ::= { hpnsaEventLog 3 }
    hpnsaEventLogPresenceId OBJECT IDENTIFIER ::= { hpnsaEventLog 4 }
    hpnsaEventLogStatistics OBJECT IDENTIFIER ::= { hpnsaEventLog 5 }

-- *************************************************************************
-- hpnsaEventLogMibRev (1.3.6.1.4.1.11.2.23.19.1)
-- **************************************************************************

hpnsaEventLogMibRevMajor OBJECT-TYPE
    SYNTAX INTEGER (0..65535)
    ACCESS read-only
    STATUS mandatory
    DESCRIPTION
	"The major revision level of the MIB (left of the decimal)."
    ::= { hpnsaEventLogRev 1 }

hpnsaEventLogMibRevMinor OBJECT-TYPE
    SYNTAX INTEGER (0..65535)
    ACCESS read-only
    STATUS mandatory
    DESCRIPTION
	"The minor revision level of the MIB (right of the decimal)."
    ::= { hpnsaEventLogRev 2 }


-- *************************************************************************
-- hpnsaEventLogAgentInfo (1.3.6.1.4.1.11.2.23.19.2)
-- **************************************************************************

hpnsaEventLogAgentTable OBJECT-TYPE
    SYNTAX  SEQUENCE OF HPnsaEventLogAgentEntry
    ACCESS  not-accessible
    STATUS  mandatory
    DESCRIPTION
	"A table of SNMP Agents that satisfy requests for this MIB."
    ::= { hpnsaEventLogAgentInfo 1 }

hpnsaEventLogAgentEntry OBJECT-TYPE
    SYNTAX  HPnsaEventLogAgentEntry
    ACCESS  not-accessible
    STATUS  mandatory
    DESCRIPTION
	"A description of the agents that access the hardware log"
    INDEX   { hpnsaEventLogAgentIndex }
    ::= { hpnsaEventLogAgentTable 1 }
       
HPnsaEventLogAgentEntry ::= SEQUENCE {
    hpnsaEventLogAgentIndex       INTEGER,
    hpnsaEventLogAgentName        DisplayString,
    hpnsaEventLogAgentVersion     DisplayString,
    hpnsaEventLogAgentDate        OCTET STRING
}


hpnsaEventLogAgentIndex OBJECT-TYPE
    SYNTAX  INTEGER (0..255)
    ACCESS  read-only
    STATUS  mandatory
    DESCRIPTION
	"A unique index for this module description."
    ::= { hpnsaEventLogAgentEntry 1 }

hpnsaEventLogAgentName OBJECT-TYPE
    SYNTAX  DisplayString (SIZE (0..255))
    ACCESS  read-only
    STATUS  mandatory
    DESCRIPTION
       "Name of the Agent/Agents satisfying SNMP requests for this MIB."
    ::= { hpnsaEventLogAgentEntry 2 }

hpnsaEventLogAgentVersion OBJECT-TYPE
    SYNTAX  DisplayString (SIZE (0..5))
    ACCESS  read-only
    STATUS  mandatory
    DESCRIPTION
       "Version number of the Agent/Agents satisfying SNMP requests for
       this MIB."
    ::= { hpnsaEventLogAgentEntry 3 }

hpnsaEventLogAgentDate OBJECT-TYPE
    SYNTAX  OCTET STRING (SIZE (6))
    ACCESS  read-only
    STATUS  mandatory
    DESCRIPTION
	 "The date on which this Agent was created.

	 field  octets  contents                  range
	 _________________________________________________
	   1       1    years since 1900          0..255
	   2       2    month                     1..12
	   3       3    day                       1..31
	   4       4    hour                      0..23
	   5       5    minute                    0..59  
	   6       6    second                    0..59
	     "
      ::= { hpnsaEventLogAgentEntry 4 }
 


-- *************************************************************************
-- hpnsaEventAgentCfgInfo (1.3.6.1.4.1.11.2.23.19.3)
-- **************************************************************************

hpnsaEventCfgTable OBJECT-TYPE
    SYNTAX SEQUENCE OF HPnsaEventCfgTableEntry
    ACCESS not-accessible
    STATUS mandatory
    DESCRIPTION
	"A table that contains all supported event log records on 
	 the server and a flag indicating whether or not an SNMP trap 
	 needs to be sent when a particular event occurs.
	 Table is indexed by the record type"
    ::= { hpnsaEventAgentCfgInfo 1 }

hpnsaEventCfgTableEntry OBJECT-TYPE
    SYNTAX HPnsaEventCfgTableEntry
    ACCESS not-accessible
    STATUS mandatory
    DESCRIPTION 
	"A particular log event type along with the flag indicating 
	 whether or not an SNMP trap needs to be sent when that 
	 event occurs. "
    INDEX { hpnsaEventLogRecType }
    ::= { hpnsaEventCfgTable 1 }


HPnsaEventCfgTableEntry ::= SEQUENCE {
    hpnsaEventLogRecType        INTEGER,
    hpnsaEventLogRecTrapEnable  INTEGER
}



hpnsaEventLogRecType OBJECT-TYPE
    SYNTAX INTEGER {
	errorEccSingleBit(1),
	errorEccMultipleBit(2),
	errorParityMemory(3),
	errorBusTimeout(4),
	errorIOChannelCheck(5),
	errorSoftwareNMI(6),
	errorPostMemoryResize(7),
	errorPost(8),
	errorPciParity(9),
	errorPciSystem(10),
	errorCpuFailure(11),
	errorFailsafeTimeout(12),
	infoSingleBitErrorDisabled(13),
	infoErrorLoggingDisabled(14),
	errorSystemLimitExceeded(16),
	infoAsynchronousSystemReset(17),
	infoSystemReconfig(20),
	errorPCISystem(21),
	logAreaReset(22),
	systemRebooted(23),
	errorECCSingleBit(33),
	errorECCMultipleBit(34),
	errorPOSTMemoryResize(35),
	cpuDeconfigured(128),
	p6ECCError(129),
	frontPanelNMI(130),
	cpuPciSingleFanError(131),
	cpuPciMultipleFanError(132),
	cpuPciFanRestored(133),
	watchdogTimerReset(134),
	memorySingleFanError(135),
	memoryMultipleFanError(136),
	memoryFanRestored(137),
	cpuReconfigured(138),
	powerSupplyEvent(139),
	powerSupplyRemoved(140),
	powerSupplyInserted(141),
	controlBoardReset(142),
	controlBoardPowerCycle(143),
	cpuCardMissing(144),
	voltageRegulatingMonitorFailure(145),
	infoRedundantPowerSupply(247),
	infoHotSwapModule(248)
    }
    ACCESS read-only
    STATUS mandatory
    DESCRIPTION 
	"Type of a log event"
    ::= { hpnsaEventCfgTableEntry 1 }


hpnsaEventLogRecTrapEnable OBJECT-TYPE
    SYNTAX INTEGER {
	trapDisabled(1),
	trapEnabled(2)
    }
    ACCESS read-write
    STATUS mandatory
    DESCRIPTION 
	"Set the value to trapEnabled if you want the event log agent to send 
	 SNMP traps when an event of this type occurs. Set it to trapDisabled 
	 otherwise."
    ::= { hpnsaEventCfgTableEntry 2 }



-- *************************************************************************
-- hpnsaEventLogPresenceId (1.3.6.1.4.1.11.2.23.19.4)
-- **************************************************************************

hpnsaEccPresent OBJECT-TYPE
    SYNTAX INTEGER (0..1)
    ACCESS read-only
    STATUS mandatory
    DESCRIPTION 
	"Determines whether ECC memory errors are being logged in
	 the hardware log"
    ::= { hpnsaEventLogPresenceId 1 }


hpnsaPostPresent OBJECT-TYPE
    SYNTAX INTEGER (0..1)
    ACCESS read-only
    STATUS mandatory
    DESCRIPTION 
	"Determines whether Post Errors are being logged in 
	the hardware log"
    ::= { hpnsaEventLogPresenceId 2 }


hpnsaTempVoltagePresent OBJECT-TYPE
    SYNTAX INTEGER (0..1)
    ACCESS read-only
    STATUS mandatory
    DESCRIPTION 
	"Determines whether Temperature sensor warnings are 
	being logged in the hardware log"
    ::= { hpnsaEventLogPresenceId 3 }


hpnsaASRPresent OBJECT-TYPE
    SYNTAX INTEGER (0..1)
    ACCESS read-only
    STATUS mandatory
    DESCRIPTION 
	"Determines whether ASR service is present on the server"
    ::= { hpnsaEventLogPresenceId 4 }


hpnsaNMIPresent OBJECT-TYPE
    SYNTAX INTEGER (0..1)
    ACCESS read-only
    STATUS mandatory
    DESCRIPTION 
	"Determines whether software NMI errors are being logged 
	in the hardware log"
    ::= { hpnsaEventLogPresenceId 5 }



-- *************************************************************************
-- hpnsaEventLogStatistics (1.3.6.1.4.1.11.2.23.19.5)
-- **************************************************************************

hpnsaEventLogPercentFull OBJECT-TYPE
    SYNTAX INTEGER (0..100)
    ACCESS read-only
    STATUS mandatory
    DESCRIPTION 
	"Percentage of the Event Log area occupied by 
    the event record entries"
    ::= { hpnsaEventLogStatistics 1 }


hpnsaEventLogLastErasedDate OBJECT-TYPE
    SYNTAX  OCTET STRING (SIZE (6))
    ACCESS  read-only
    STATUS  mandatory
    DESCRIPTION
	 "The date and time the event log area was last erased

	 field  octets  contents                  range
	 _________________________________________________
	   1       1    years since 1900          0..255
	   2       2    month                     1..12
	   3       3    day                       1..31
	   4       4    hour                      0..23
	   5       5    minute                    0..59  
	   6       6    second                    0..59
	     "
    ::= { hpnsaEventLogStatistics 2 }


hpnsaEventLogErasures OBJECT-TYPE
    SYNTAX Counter
    ACCESS read-only
    STATUS mandatory
    DESCRIPTION 
	"Number of times the logging area has been erased"
    ::= { hpnsaEventLogStatistics 3 }


hpnsaEventLogEraseLog OBJECT-TYPE
    SYNTAX INTEGER {
	eraseLogNow(1234)
    }
    ACCESS read-write
    STATUS mandatory
    DESCRIPTION
	 "Set this variable to integer value of 1234 in order 
	  to erase the entire log area the next time the agent polls"
    ::= { hpnsaEventLogStatistics 4 }


hpnsaEventLogTable OBJECT-TYPE
    SYNTAX SEQUENCE OF HPnsaEventLogTableEntry
    ACCESS not-accessible
    STATUS mandatory
    DESCRIPTION
	"A table that contains all log events since the last
	 time the log was cleared"
    ::= { hpnsaEventLogStatistics 5 }


hpnsaEventLogTableEntry OBJECT-TYPE
    SYNTAX HPnsaEventLogTableEntry
    ACCESS not-accessible
    STATUS mandatory
    DESCRIPTION 
	"Description of a log event"
    INDEX { hpnsaEventLogTableIndex }
    ::= { hpnsaEventLogTable 1 }


HPnsaEventLogTableEntry ::= SEQUENCE {
    hpnsaEventLogTableIndex     INTEGER,
    hpnsaEventLogEntryDate      OCTET STRING,
    hpnsaEventLogEntryDescr         DisplayString,
    hpnsaEventLogEntryTrapID        DisplayString,
    hpnsaEventLogEntryVB1           DisplayString,
    hpnsaEventLogEntryVB2           DisplayString,
    hpnsaEventLogEntryVB3           DisplayString,
    hpnsaEventLogEntryVB4           DisplayString,
    hpnsaEventLogEntryVB5           DisplayString,
    hpnsaEventLogEntryVB6           DisplayString,
    hpnsaEventLogEntryVB7           DisplayString,
    hpnsaEventLogEntryVB8           DisplayString,
    hpnsaEventLogEntryAdvisory      DisplayString,
    hpnsaEventLogEntryReportEntity  DisplayString,
    hpnsaEventLogEntrySeverity	    DisplayString,	
    hpnsaEventLogEntryStatus	    INTEGER,	
    hpnsaEventLogEntryInfo 	    INTEGER,	
    hpnsaEventLogEntryUpdateTime    OCTET STRING	
}


hpnsaEventLogTableIndex OBJECT-TYPE
    SYNTAX  INTEGER
    ACCESS  read-only
    STATUS  mandatory
    DESCRIPTION
	"A unique index for event"
    ::= { hpnsaEventLogTableEntry 1 }


hpnsaEventLogEntryDate OBJECT-TYPE
    SYNTAX  OCTET STRING (SIZE (6))
    ACCESS  read-only
    STATUS  mandatory
    DESCRIPTION
	 "The date on which this event occured

	 field  octets  contents                  range
	 _________________________________________________
	   1       1    years since 1900          0..255
	   2       2    month                     1..12
	   3       3    day                       1..31
	   4       4    hour                      0..23
	   5       5    minute                    0..59  
	   6       6    second                    0..59
	     "
      ::= { hpnsaEventLogTableEntry 2 }
 
hpnsaEventLogEntryDescr OBJECT-TYPE
    SYNTAX  DisplayString (SIZE (0..255))
    ACCESS  read-only
    STATUS  mandatory
    DESCRIPTION
       "Description of this log event, including the date and time when
	the event occured"
    ::= { hpnsaEventLogTableEntry 3 }

hpnsaEventLogEntryTrapID OBJECT-TYPE
    SYNTAX  DisplayString (SIZE (0..255))
    ACCESS  read-only
    STATUS  mandatory
    DESCRIPTION
       "Trap Id."
    ::= { hpnsaEventLogTableEntry 4 }

hpnsaEventLogEntryVB1 OBJECT-TYPE
    SYNTAX  DisplayString (SIZE (0..255))
    ACCESS  read-only
    STATUS  mandatory
    DESCRIPTION
	 "Varbind #1."
    ::= { hpnsaEventLogTableEntry 5 }

hpnsaEventLogEntryVB2 OBJECT-TYPE
    SYNTAX  DisplayString (SIZE (0..255))
    ACCESS  read-only
    STATUS  mandatory
    DESCRIPTION
	 "Varbind #2."
    ::= { hpnsaEventLogTableEntry 6 }

hpnsaEventLogEntryVB3 OBJECT-TYPE
    SYNTAX  DisplayString (SIZE (0..255))
    ACCESS  read-only
    STATUS  mandatory
    DESCRIPTION
	 "Varbind #3."
    ::= { hpnsaEventLogTableEntry 7 }

hpnsaEventLogEntryVB4 OBJECT-TYPE
    SYNTAX  DisplayString (SIZE (0..255))
    ACCESS  read-only
    STATUS  mandatory
    DESCRIPTION
	 "Varbind #4."
    ::= { hpnsaEventLogTableEntry 8 }

hpnsaEventLogEntryVB5 OBJECT-TYPE
    SYNTAX  DisplayString (SIZE (0..255))
    ACCESS  read-only
    STATUS  mandatory
    DESCRIPTION
	 "Varbind #5."
    ::= { hpnsaEventLogTableEntry 9 }

hpnsaEventLogEntryVB6 OBJECT-TYPE
    SYNTAX  DisplayString (SIZE (0..255))
    ACCESS  read-only
    STATUS  mandatory
    DESCRIPTION
	 "Varbind #6."
    ::= { hpnsaEventLogTableEntry 10 }

hpnsaEventLogEntryVB7 OBJECT-TYPE
    SYNTAX  DisplayString (SIZE (0..255))
    ACCESS  read-only
    STATUS  mandatory
    DESCRIPTION
	 "Varbind #7."
    ::= { hpnsaEventLogTableEntry 11 }

hpnsaEventLogEntryVB8 OBJECT-TYPE
    SYNTAX  DisplayString (SIZE (0..255))
    ACCESS  read-only
    STATUS  mandatory
    DESCRIPTION
	 "Varbind #8."
    ::= { hpnsaEventLogTableEntry 12 }
 
hpnsaEventLogEntryAdvisory OBJECT-TYPE
    SYNTAX  DisplayString (SIZE (0..1023))
    ACCESS  read-only
    STATUS  mandatory
    DESCRIPTION
	 "Advisory or help text"
    ::= { hpnsaEventLogTableEntry 13 }

hpnsaEventLogEntryReportEntity OBJECT-TYPE
    SYNTAX  DisplayString (SIZE (0..255))
    ACCESS  read-only
    STATUS  mandatory
    DESCRIPTION
	 "Reporting entity of this event"
    ::= { hpnsaEventLogTableEntry 14 }


hpnsaEventLogEntrySeverity OBJECT-TYPE
    SYNTAX  DisplayString (SIZE (0..255))
    ACCESS  read-only
    STATUS  mandatory
    DESCRIPTION
	 "Severity of this event"
    ::= { hpnsaEventLogTableEntry 15 }

hpnsaEventLogEntryStatus OBJECT-TYPE
        SYNTAX  INTEGER {
            informational(2),   -- informational with no action required
            infoWithAlert(3),   -- informational but with LCD alert message
            repaired(6),        -- corrective action taken
            caution(9),         -- non-fatal error condition
            critical(15)        -- component failure
            }
    ACCESS  read-write
    STATUS  mandatory
    DESCRIPTION
            "This value specifies the severity status of the event log entry.
	     The event severity can be set to a desired value such as repaired."
    ::= { hpnsaEventLogTableEntry 16 }

hpnsaEventLogEntryInfo OBJECT-TYPE
    SYNTAX  INTEGER 
    ACCESS  read-only
    STATUS  mandatory
    DESCRIPTION
	 "This variable contains the following info about the event:
         Bit 31..3  = reserved
         Bit 2: 0 = not-repairable, 1 = repairable
         Bit 1..0: 0 = not impacting local partition, 1 = impacting local partition, 2 = unknown"
    ::= { hpnsaEventLogTableEntry 17 }


hpnsaEventLogEntryUpdateTime OBJECT-TYPE
    SYNTAX  OCTET STRING (SIZE (6))
    ACCESS  read-only
    STATUS  mandatory
    DESCRIPTION
	 "The date on which this event occured

	 field  octets  contents                  range
	 _________________________________________________
	   1       1    years since 1900          0..255
	   2       2    month                     1..12
	   3       3    day                       1..31
	   4       4    hour                      0..23
	   5       5    minute                    0..59  
	   6       6    second                    0..59
	     "
      ::= { hpnsaEventLogTableEntry 18 }


hpnsaEventLogNumberOfEvents OBJECT-TYPE
    SYNTAX INTEGER
    ACCESS read-only
    STATUS mandatory
    DESCRIPTION
	 "This variable indicates the number of events in the event log table."
    ::= { hpnsaEventLogStatistics 6 }

hpnsaEventLogAggregationStatus OBJECT-TYPE
    SYNTAX  INTEGER {
            other(1),
            ok(2),
            degraded(3),
            failed(4)
            }
    ACCESS read-only
    STATUS mandatory
    DESCRIPTION
	 "This variable indicates the SEL aggregation status."
    ::= { hpnsaEventLogStatistics 7 }


hpnsaEventLogLocalTable OBJECT-TYPE
    SYNTAX SEQUENCE OF HPnsaEventLogLocalTableEntry
    ACCESS not-accessible
    STATUS mandatory
    DESCRIPTION
	"A table that contains all log events in the local soft log since the last
	 time the log was cleared"
    ::= { hpnsaEventLogStatistics 8 }


hpnsaEventLogLocalTableEntry OBJECT-TYPE
    SYNTAX HPnsaEventLogLocalTableEntry
    ACCESS not-accessible
    STATUS mandatory
    DESCRIPTION 
	"Description of a log event in the local soft log"
    INDEX { hpnsaEventLogTableIndex }
    ::= { hpnsaEventLogLocalTable 1 }


HPnsaEventLogLocalTableEntry ::= SEQUENCE {
    hpnsaEventLogLocalTableIndex     INTEGER,
    hpnsaEventLogLocalEntryDate      OCTET STRING,
    hpnsaEventLogLocalEntryDescr         DisplayString,
    hpnsaEventLogLocalEntryTrapID        DisplayString,
    hpnsaEventLogLocalEntryVB1           DisplayString,
    hpnsaEventLogLocalEntryVB2           DisplayString,
    hpnsaEventLogLocalEntryVB3           DisplayString,
    hpnsaEventLogLocalEntryVB4           DisplayString,
    hpnsaEventLogLocalEntryVB5           DisplayString,
    hpnsaEventLogLocalEntryVB6           DisplayString,
    hpnsaEventLogLocalEntryVB7           DisplayString,
    hpnsaEventLogLocalEntryVB8           DisplayString,
    hpnsaEventLogLocalEntryAdvisory      DisplayString,
    hpnsaEventLogLocalEntryReportEntity  DisplayString,
    hpnsaEventLogLocalEntrySeverity	    DisplayString,	
    hpnsaEventLogLocalEntryStatus	    INTEGER,	
    hpnsaEventLogLocalEntryInfo 	    INTEGER,	
    hpnsaEventLogLocalEntryUpdateTime    OCTET STRING	
}


hpnsaEventLogLocalTableIndex OBJECT-TYPE
    SYNTAX  INTEGER
    ACCESS  read-only
    STATUS  mandatory
    DESCRIPTION
	"A unique index for event in the local soft log"
    ::= { hpnsaEventLogLocalTableEntry 1 }


hpnsaEventLogLocalEntryDate OBJECT-TYPE
    SYNTAX  OCTET STRING (SIZE (6))
    ACCESS  read-only
    STATUS  mandatory
    DESCRIPTION
	 "The date on which this event occured

	 field  octets  contents                  range
	 _________________________________________________
	   1       1    years since 1900          0..255
	   2       2    month                     1..12
	   3       3    day                       1..31
	   4       4    hour                      0..23
	   5       5    minute                    0..59  
	   6       6    second                    0..59
	     "
      ::= { hpnsaEventLogLocalTableEntry 2 }
 
hpnsaEventLogLocalEntryDescr OBJECT-TYPE
    SYNTAX  DisplayString (SIZE (0..255))
    ACCESS  read-only
    STATUS  mandatory
    DESCRIPTION
       "Description of this log event, including the date and time when
	the event occured"
    ::= { hpnsaEventLogLocalTableEntry 3 }

hpnsaEventLogLocalEntryTrapID OBJECT-TYPE
    SYNTAX  DisplayString (SIZE (0..255))
    ACCESS  read-only
    STATUS  mandatory
    DESCRIPTION
       "Trap Id."
    ::= { hpnsaEventLogLocalTableEntry 4 }

hpnsaEventLogLocalEntryVB1 OBJECT-TYPE
    SYNTAX  DisplayString (SIZE (0..255))
    ACCESS  read-only
    STATUS  mandatory
    DESCRIPTION
	 "Varbind #1."
    ::= { hpnsaEventLogLocalTableEntry 5 }

hpnsaEventLogLocalEntryVB2 OBJECT-TYPE
    SYNTAX  DisplayString (SIZE (0..255))
    ACCESS  read-only
    STATUS  mandatory
    DESCRIPTION
	 "Varbind #2."
    ::= { hpnsaEventLogLocalTableEntry 6 }

hpnsaEventLogLocalEntryVB3 OBJECT-TYPE
    SYNTAX  DisplayString (SIZE (0..255))
    ACCESS  read-only
    STATUS  mandatory
    DESCRIPTION
	 "Varbind #3."
    ::= { hpnsaEventLogLocalTableEntry 7 }

hpnsaEventLogLocalEntryVB4 OBJECT-TYPE
    SYNTAX  DisplayString (SIZE (0..255))
    ACCESS  read-only
    STATUS  mandatory
    DESCRIPTION
	 "Varbind #4."
    ::= { hpnsaEventLogLocalTableEntry 8 }

hpnsaEventLogLocalEntryVB5 OBJECT-TYPE
    SYNTAX  DisplayString (SIZE (0..255))
    ACCESS  read-only
    STATUS  mandatory
    DESCRIPTION
	 "Varbind #5."
    ::= { hpnsaEventLogLocalTableEntry 9 }

hpnsaEventLogLocalEntryVB6 OBJECT-TYPE
    SYNTAX  DisplayString (SIZE (0..255))
    ACCESS  read-only
    STATUS  mandatory
    DESCRIPTION
	 "Varbind #6."
    ::= { hpnsaEventLogLocalTableEntry 10 }

hpnsaEventLogLocalEntryVB7 OBJECT-TYPE
    SYNTAX  DisplayString (SIZE (0..255))
    ACCESS  read-only
    STATUS  mandatory
    DESCRIPTION
	 "Varbind #7."
    ::= { hpnsaEventLogLocalTableEntry 11 }

hpnsaEventLogLocalEntryVB8 OBJECT-TYPE
    SYNTAX  DisplayString (SIZE (0..255))
    ACCESS  read-only
    STATUS  mandatory
    DESCRIPTION
	 "Varbind #8."
    ::= { hpnsaEventLogLocalTableEntry 12 }
 
hpnsaEventLogLocalEntryAdvisory OBJECT-TYPE
    SYNTAX  DisplayString (SIZE (0..1023))
    ACCESS  read-only
    STATUS  mandatory
    DESCRIPTION
	 "Advisory or help text"
    ::= { hpnsaEventLogLocalTableEntry 13 }

hpnsaEventLogLocalEntryReportEntity OBJECT-TYPE
    SYNTAX  DisplayString (SIZE (0..255))
    ACCESS  read-only
    STATUS  mandatory
    DESCRIPTION
	 "Reporting entity of this event"
    ::= { hpnsaEventLogLocalTableEntry 14 }


hpnsaEventLogLocalEntrySeverity OBJECT-TYPE
    SYNTAX  DisplayString (SIZE (0..255))
    ACCESS  read-only
    STATUS  mandatory
    DESCRIPTION
	 "Severity of this event"
    ::= { hpnsaEventLogLocalTableEntry 15 }

hpnsaEventLogLocalEntryStatus OBJECT-TYPE
        SYNTAX  INTEGER {
            informational(2),   -- informational with no action required
            infoWithAlert(3),   -- informational but with LCD alert message
            repaired(6),        -- corrective action taken
            caution(9),         -- non-fatal error condition
            critical(15)        -- component failure
            }
    ACCESS  read-write
    STATUS  mandatory
    DESCRIPTION
            "This value specifies the severity status of the event log entry.
	     The event severity can be set to a desired value such as repaired."
    ::= { hpnsaEventLogLocalTableEntry 16 }

hpnsaEventLogLocalEntryInfo OBJECT-TYPE
    SYNTAX  INTEGER 
    ACCESS  read-only
    STATUS  mandatory
    DESCRIPTION
	 "This variable contains the following info about the event:
         Bit 31..3  = reserved
         Bit 2: 0 = not-repairable, 1 = repairable
         Bit 1..0: 0 = not impacting local partition, 1 = impacting local partition, 2 = unknown"
    ::= { hpnsaEventLogLocalTableEntry 17 }


hpnsaEventLogLocalEntryUpdateTime OBJECT-TYPE
    SYNTAX  OCTET STRING (SIZE (6))
    ACCESS  read-only
    STATUS  mandatory
    DESCRIPTION
	 "The date on which this event occured

	 field  octets  contents                  range
	 _________________________________________________
	   1       1    years since 1900          0..255
	   2       2    month                     1..12
	   3       3    day                       1..31
	   4       4    hour                      0..23
	   5       5    minute                    0..59  
	   6       6    second                    0..59
	     "
      ::= { hpnsaEventLogLocalTableEntry 18 }


hpnsaEventLogNumOfLocalEvents OBJECT-TYPE
    SYNTAX INTEGER
    ACCESS read-only
    STATUS mandatory
    DESCRIPTION
	 "This variable indicates the number of events in the local event log table."
    ::= { hpnsaEventLogStatistics 9 }

END
