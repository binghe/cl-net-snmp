-- Linux-HA: SNMP Subagent
-- 
-- Copyright (C) 2002 Yixiong Zou (yixiong.zou@intel.com)
--
-- This program is free software; you can redistribute it and/or
-- modify it under the terms of the GNU General Public License
-- as published by the Free Software Foundation; either version 2
-- of the License, or (at your option) any later version.
-- 
-- This program is distributed in the hope that it will be useful,
-- but WITHOUT ANY WARRANTY; without even the implied warranty of
-- MERCHANTABILITY or FITNESS FOR A PARTICULAR PURPOSE.  See the
-- GNU General Public License for more details.
-- 
-- You should have received a copy of the GNU General Public License
-- along with this program; if not, write to the Free Software
-- Foundation, Inc., 59 Temple Place - Suite 330, Boston, MA  02111-1307, USA.
--

LINUX-HA-MIB DEFINITIONS ::= BEGIN

IMPORTS
    MODULE-IDENTITY, OBJECT-TYPE, enterprises,
    Counter32, INTEGER, Integer32, Unsigned32, IpAddress
	FROM SNMPv2-SMI

    TEXTUAL-CONVENTION, DisplayString, 
    TimeStamp, TruthValue, DateAndTime			    
	FROM SNMPv2-TC

    MODULE-COMPLIANCE, OBJECT-GROUP		    
	FROM SNMPv2-CONF;

linuxHA	MODULE-IDENTITY
    LAST-UPDATED "200211040000Z"	-- Nov. 4, 2002
    ORGANIZATION "High-Availability Linux Project"
    CONTACT-INFO
	"Alan Robertson
	Postal:	Linux-HA Project
		13750 Bayberry Drive
		Broomfield, CO 80020-6163
	Phone:	303-466-7405
	FAX:	n/a
	Email:	alanr@unix.sh

	Yixiong Zou
	Postal: Intel Corp.  
		CO5-162
		15400 NW Greenbrier Parkway
		Beaverton, OR 97006
		USA
	Phone:	503-677-4988
	Fax:	503-677-6670
	Email:	yixiong.zou@intel.com

	In addition, the Linux-HA mailing list is where all the 
	discussion about this MIB happens. To join the mailing list, 
	send a request message to linux-ha-subscribe@muc.de.  
	The mailing list address is
	linux-ha-dev@lists.community.tummy.com."
    DESCRIPTION
	"This MIB can be used to manage a Linux-HA cluster. The
	initial plan is to make the heartbeat, resource managment,
	and memberships accessible through SNMP. Hopefully more
	things can be added as Linux-HA matures."

    REVISION "200211040000Z"	    -- Nov. 4, 2002
    DESCRIPTION
	"The original version of this MIB."
    ::= { enterprises 4682 }

-- Current LinuxHA core MIB entries
--  lhaClusterInfo 	      OBJECT IDENTIFIER ::= { linuxHA 1 }
--  lhaNodeTable	      OBJECT IDENTIFIER ::= { linuxHA 2 }
--  lhaIFStatusTable	      OBJECT IDENTIFIER ::= { linuxHA 3 }
--  lhaResourceGroupTable     OBJECT IDENTIFIER ::= { linuxHA 4 }
--  lhaMembershipTable	      OBJECT IDENTIFIER ::= { linuxHA 6 }
--  lhaHeartbeatConfigInfo    OBJECT IDENTIFIER ::= { linuxHA 7 }
--  lhaTrapTable	      OBJECT IDENTIFIER ::= { linuxHA 900 }

LHAUUIDString ::= TEXTUAL-CONVENTION
    DISPLAY-HINT "4x-2x-2x-2x-4x2x"
    STATUS       current
    DESCRIPTION
    	"A string that represents a UUID"
    SYNTAX       OCTET STRING (SIZE (16))

lhaClusterInfo		OBJECT IDENTIFIER ::= { linuxHA 1 }

lhaTotalNodeCount OBJECT-TYPE
    SYNTAX	Counter32
    MAX-ACCESS	read-only
    STATUS	current
    DESCRIPTION
	"The number of nodes that are currently configured for this
	cluster."
    ::= { lhaClusterInfo 1 }

lhaLiveNodeCount OBJECT-TYPE
    SYNTAX	Counter32
    MAX-ACCESS	read-only
    STATUS	current
    DESCRIPTION
	"The number of nodes that are currently active in this
	cluster."
    ::= { lhaClusterInfo 2 }

lhaCurrentNodeID OBJECT-TYPE
    SYNTAX	Integer32
    MAX-ACCESS	read-only
    STATUS	current
    DESCRIPTION
	"The nodes id of the host that this agent currently
	represents.  This value is the same as the lhaNodeIndex value
	of this node."
    ::= { lhaClusterInfo 3 }

lhaResourceGroupCount OBJECT-TYPE
    SYNTAX	Counter32
    MAX-ACCESS	read-only
    STATUS	current
    DESCRIPTION
	"The total number of Resource Groups that have been
	configured for this cluster."
    ::= { lhaClusterInfo 4 }

lhaNodeTable OBJECT-TYPE
    SYNTAX	SEQUENCE OF LHANodeEntry
    MAX-ACCESS	not-accessible
    STATUS	current
    DESCRIPTION
	"A table contains information about all the nodes in the
	cluster."
    ::= { linuxHA 2 }

lhaNodeEntry OBJECT-TYPE
    SYNTAX	LHANodeEntry
    MAX-ACCESS	not-accessible
    STATUS	current
    DESCRIPTION	
	"An entry containing a node and its statistics."
    INDEX	{ lhaNodeIndex }
    ::= { lhaNodeTable 1 }

LHANodeEntry ::= SEQUENCE {
    lhaNodeIndex	    Integer32,
    lhaNodeName	    	    DisplayString,
    lhaNodeType		    INTEGER,
    lhaNodeStatus           INTEGER,
    lhaNodeUUID		    DisplayString,
    lhaNodeIFCount	    Counter32,
}

lhaNodeIndex OBJECT-TYPE    
    SYNTAX	Integer32 (0..65535)
    MAX-ACCESS	not-accessible
    STATUS	current
    DESCRIPTION
	"An integer that identifies a node in a cluster for a given
	snmp session."
    ::= { lhaNodeEntry 1 }

lhaNodeName OBJECT-TYPE
    SYNTAX	DisplayString
    MAX-ACCESS	read-only
    STATUS	current
    DESCRIPTION
	"A human readable name that represents that node."
    ::= { lhaNodeEntry 2 }

lhaNodeType OBJECT-TYPE
    SYNTAX	INTEGER {
	    	    unknown (0),
		    normal (1),
		    ping (2)
	    	}
    MAX-ACCESS	read-only
    STATUS	current
    DESCRIPTION
	"There could be many types of nodes in the cluster.  For
	example, a node could be a normal node, or a ping node
	depending on the configuration.  This object shows the
	type of this node as an integer.  
	
	So far only the normal node and ping node are defined.  All
	the rest will fall into the 'unknown' catagory. "
    ::= { lhaNodeEntry 3 }

lhaNodeStatus OBJECT-TYPE
    SYNTAX	INTEGER {
	    	    unknown (0),
		    init (1),
		    up (2),
		    active (3), 
		    dead (4)
	    	}
    MAX-ACCESS	read-only
    STATUS	current
    DESCRIPTION
	"The status of the node as an integer. For heartbeat, this
	would normally be init, up, active, or dead.

	So far, only these four states are defined.  All the rest
	falls in 'unknown' catagory."
    ::= { lhaNodeEntry 4 }

lhaNodeUUID OBJECT-TYPE
    SYNTAX	LHAUUIDString
    MAX-ACCESS	read-only
    STATUS	current
    DESCRIPTION
	"The UUID of the current node in string representatio.  This
	UUID will be persisted over the heartbeat session.  So it can
	be used as a unique identifier for a node."
    ::= { lhaNodeEntry 5 }

lhaNodeIFCount OBJECT-TYPE
    SYNTAX	Counter32
    MAX-ACCESS	read-only
    STATUS	current
    DESCRIPTION
	"The number of interfaces that is used by heartbeat
	for this node."
    ::= { lhaNodeEntry 6 }

lhaIFStatusTable OBJECT-TYPE
    SYNTAX	SEQUENCE OF LHAIFEntry
    MAX-ACCESS	not-accessible
    STATUS	current
    DESCRIPTION
	"A table describes all the interfaces that are used by the
	heartbeat cluster."
    ::= { linuxHA 3 }

lhaIFStatusEntry OBJECT-TYPE
    SYNTAX	LHAIFStatusEntry
    MAX-ACCESS	not-accessible
    STATUS	current
    DESCRIPTION
	"An entry containing information about that interface.
	The lhaNodeIndex is listed in the lhaNodeTable."
    INDEX	{ lhaNodeIndex, lhaIFIndex }
    ::= { lhaIFStatusTable 1 }

LHAIFStatusEntry ::= SEQUENCE {
    lhaIFIndex	    	Integer32,
    lhaIFName	    	DisplayString,
    lhaIFStatus		INTEGER
}

lhaIFIndex OBJECT-TYPE
    SYNTAX	Integer32 (0..65535)
    MAX-ACCESS	not-accessible
    STATUS	current
    DESCRIPTION
	"An unique integer identifies this interface."
    ::= { lhaIFStatusEntry 1 }

lhaIFName OBJECT-TYPE
    SYNTAX	DisplayString
    MAX-ACCESS	read-only
    STATUS	current
    DESCRIPTION
	"A name for this interface."
    ::= { lhaIFStatusEntry 2 }

lhaIFStatus OBJECT-TYPE
    SYNTAX	INTEGER {
	    	    unknown (0),
		    up (1),
		    down (2)
    		}
    MAX-ACCESS	read-only
    STATUS	current
    DESCRIPTION
	"The status for this interface as an integer. 
	
	Currently only up and down are defined as the interface
	status.  All the others will fall into the unknown catagory."
    ::= { lhaIFStatusEntry 3 }


lhaResourceGroupTable OBJECT-TYPE
    SYNTAX	SEQUENCE OF LHAResourceGroupEntry
    MAX-ACCESS	not-accessible
    STATUS	current
    DESCRIPTION
	"A table containing information of all the resource groups."
    ::= { linuxHA 4 }

lhaResourceGroupEntry OBJECT-TYPE
    SYNTAX	LHAResourceGroupEntry
    MAX-ACCESS	not-accessible
    STATUS	current
    DESCRIPTION
	"An entry that describes the resource group and its
	information."
    INDEX	{ lhaResourceGroupIndex }
    ::= { lhaResourceGroupTable 1 }

LHAResourceGroupEntry ::= SEQUENCE	{
    lhaResourceGroupIndex	Integer32,
    lhaResourceGroupMaster	DisplayString,
    lhaResourceGroupResources   DisplayString,
    lhaResourceGroupStatus	Integer32
}

lhaResourceGroupIndex OBJECT-TYPE
    SYNTAX	Integer32 (0..65535)
    MAX-ACCESS	not-accessible
    STATUS	current
    DESCRIPTION
	"A unique integer that identifies this resource group."
    ::= { lhaResourceGroupEntry 1 }

lhaResourceGroupMaster OBJECT-TYPE
    SYNTAX	Integer32 (0..65535)
    MAX-ACCESS	read-only
    STATUS	current
    DESCRIPTION
	"The master node id of this resource group.  This is 
	the lhaNodeIndex for the master node of this resource
	group. "
    ::= { lhaResourceGroupEntry 2 }

lhaResourceGroupResources OBJECT-TYPE
    SYNTAX	DisplayString
    MAX-ACCESS	read-only
    STATUS	current
    DESCRIPTION
	"The resources contained in this resource group."
    ::= { lhaResourceGroupEntry 3 }

lhaResourceGroupStatus OBJECT-TYPE
    SYNTAX	Unsigned32 (0..255)
    MAX-ACCESS	read-only
    STATUS	current
    DESCRIPTION
	"The status of this resource group.

	 0       program is running 
	 1       program is dead and /var/run pid file exists
	 2       program is dead and /var/lock lock file exists
	 3       program is stopped
	 4-100   reserved for future LSB use
	 100-149 reserved for distribution use
	 150-199 reserved for application use
	 200-254 reserved
	 "
    ::= { lhaResourceGroupEntry 4 }

lhaMembershipTable OBJECT-TYPE
    SYNTAX	SEQUENCE OF LHAMembershipEntry
    MAX-ACCESS	not-accessible
    STATUS	current
    DESCRIPTION
	"A table containing membership information for the cluster.
	A successful membership has to have qurom.  
	
				NOTE WELL

	If this table does not contain any entries, that means the 
	node is not part of the cluster membership."
    ::= { linuxHA 6 }

lhaMembershipEntry OBJECT-TYPE
    SYNTAX	LHAMembershipEntry
    MAX-ACCESS	not-accessible
    STATUS	current
    DESCRIPTION
	"An entry containing a member and its status."
    INDEX	{ lhaMemberIndex }
    ::= { lhaMembershipTable 1 }

LHAMembershipEntry ::= SEQUENCE {
    lhaMemberIndex   		Integer32,
    lhaMemberName    		DisplayString,
    lhaMemberAddress 		DisplayString,
    lhaMemberClusterName	DisplayString,
    lhaMemberIsMember		TruthValue,
    lhaMemberLastChange 	INTEGER,
    lhaMemberBootTime 		TimeStamp,
}

lhaMemberIndex OBJECT-TYPE
    SYNTAX	Integer32 (0..65535)
    MAX-ACCESS	not-accessible
    STATUS	current
    DESCRIPTION
	"A unique integer that identifies this member."
    ::= { lhaMembershipEntry 1 }

lhaMemberName OBJECT-TYPE
    SYNTAX	DisplayString
    MAX-ACCESS	read-only
    STATUS	current
    DESCRIPTION
	"The name of the cluster member."
    ::= { lhaMembershipEntry 2 }

lhaMemberAddress OBJECT-TYPE
    SYNTAX	OCTET STRING (SIZE (64))
    MAX-ACCESS	read-only
    STATUS	current
    DESCRIPTION
	"The address of the cluster member."
    ::= { lhaMembershipEntry 3 }

lhaMemberClusterName OBJECT-TYPE
    SYNTAX	DisplayString
    MAX-ACCESS	read-only
    STATUS	current
    DESCRIPTION
	"The name of this cluster."
    ::= { lhaMembershipEntry 4 }

lhaMemberIsMember OBJECT-TYPE
    SYNTAX	TruthValue
    MAX-ACCESS	read-only
    STATUS	current
    DESCRIPTION
	"If this node is part of the membership or not."
    ::= { lhaMembershipEntry 5 }

lhaMemberLastChange OBJECT-TYPE
    SYNTAX	INTEGER {
	    	    undefined (0),
		    nochange (1),
		    joined (2),
		    left (3)
		}
    MAX-ACCESS	read-only
    STATUS	current
    DESCRIPTION
	"If this node is part of the membership or not."
    ::= { lhaMembershipEntry 6 }

lhaMemberBootTime OBJECT-TYPE
    SYNTAX	TimeStamp
    MAX-ACCESS	read-only
    STATUS	current
    DESCRIPTION
	"The time when this cluster member last started."
    ::= { lhaMembershipEntry 7 }

lhaHeartbeatConfigInfo		OBJECT IDENTIFIER ::= { linuxHA 7 }

lhaHBVersion OBJECT-TYPE
    SYNTAX	DisplayString
    MAX-ACCESS	read-only
    STATUS	current
    DESCRIPTION
	"The heartbeat version."
    ::= { lhaHeartbeatConfigInfo 1 }

lhaKeepAlive OBJECT-TYPE
    SYNTAX	DisplayString
    MAX-ACCESS	read-only
    STATUS	current
    DESCRIPTION
	"The heartbeat interval."
    ::= { lhaHeartbeatConfigInfo 3 }

lhaDeadTime OBJECT-TYPE
    SYNTAX	DisplayString
    MAX-ACCESS	read-only
    STATUS	current
    DESCRIPTION
	"The time it waits before declaring a node to be dead."
    ::= { lhaHeartbeatConfigInfo 4 }

lhaDeadPing OBJECT-TYPE
    SYNTAX	DisplayString
    MAX-ACCESS	read-only
    STATUS	current
    DESCRIPTION
	"The time it waits before declaring a ping node to be dead."
    ::= { lhaHeartbeatConfigInfo 5 }

lhaWarnTime OBJECT-TYPE
    SYNTAX	DisplayString
    MAX-ACCESS	read-only
    STATUS	current
    DESCRIPTION
	"The time it waits before issuing a 'late heartbeat' warning."
    ::= { lhaHeartbeatConfigInfo 6 }

lhaInitDead OBJECT-TYPE
    SYNTAX	DisplayString
    MAX-ACCESS	read-only
    STATUS	current
    DESCRIPTION
	"Very first dead time.  Should be twice the normal dead time."
    ::= { lhaHeartbeatConfigInfo 7 }

lhaBaudRate OBJECT-TYPE
    SYNTAX	DisplayString
    MAX-ACCESS	read-only
    STATUS	current
    DESCRIPTION
	"Baud rate for serial ports."
    ::= { lhaHeartbeatConfigInfo 9 }

lhaAutoFailBack OBJECT-TYPE
    SYNTAX	INTEGER {
	    	    undefined (0),
		    on (1),
		    off (2),
		    legacy (3)
    		}
    MAX-ACCESS	read-only
    STATUS	current
    DESCRIPTION
	"Determins whether a resource will automatically fail back to
	its primary node, or remain on whatever the node is serving.
	
	Possible values are: on, off, legacy."
    ::= { lhaHeartbeatConfigInfo 12 }

lhaStonith OBJECT-TYPE
    SYNTAX	DisplayString
    MAX-ACCESS	read-only
    STATUS	current
    DESCRIPTION
	"The STONITH device configured for this cluster."
    ::= { lhaHeartbeatConfigInfo 13 }

lhaStonithHost OBJECT-TYPE
    SYNTAX	DisplayString
    MAX-ACCESS	read-only
    STATUS	current
    DESCRIPTION
	"The STONITH host configured for this cluster."
    ::= { lhaHeartbeatConfigInfo 14 }

lhaRespawn OBJECT-TYPE
    SYNTAX	DisplayString
    MAX-ACCESS	read-only
    STATUS	current
    DESCRIPTION
	"The other services that got respawned by heartbeat daemon."
    ::= { lhaHeartbeatConfigInfo 15 }

lhaTrapTable                    OBJECT IDENTIFIER ::= { linuxHA 900 }

lhaNodeStatusUpdate NOTIFICATION-TYPE
    OBJECTS { lhaNodeName, lhaNodeStatus }
    STATUS  current
    DESCRIPTION
    	"A node status change event just happened."
    ::= { lhaTrapTable 1 }

lhaIFStatusUpdate NOTIFICATION-TYPE
    OBJECTS { lhaNodeName, lhaIFName, lhaIFStatus }
    STATUS  current
    DESCRIPTION
    	"A link status just changed."
    ::= { lhaTrapTable 3 }

lhaMembershipChange NOTIFICATION-TYPE
    OBJECTS { lhaNodeName, lhaMemberLastChange }
    STATUS  current
    DESCRIPTION
    	"A node just changed it membership. "
    ::= { lhaTrapTable 5 }

lhaHBAgentOnline NOTIFICATION-TYPE
    OBJECTS { lhaNodeName }
    STATUS  current
    DESCRIPTION
    	"The heartbeat agent for this node is online and ready to accept queries. "
    ::= { lhaTrapTable 7 }

lhaHBAgentOffline NOTIFICATION-TYPE
    OBJECTS { lhaNodeName }
    STATUS  current
    DESCRIPTION
    	"The heartbeat agent for this node is offline. "
    ::= { lhaTrapTable 9 }

END
