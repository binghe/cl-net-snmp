-- *******************************************************************
-- CISCO-LWAPP-DOT11-MIB.my 
-- January 2007, Devesh Pujari, Srinath Candadai
--
-- Copyright (c) 2007 by Cisco Systems, Inc.
-- All rights reserved.
-- *******************************************************************
--
CISCO-LWAPP-DOT11-MIB DEFINITIONS ::= BEGIN

IMPORTS 
        MODULE-IDENTITY, 
        OBJECT-TYPE,
        NOTIFICATION-TYPE,
        Unsigned32
                FROM SNMPv2-SMI
        MODULE-COMPLIANCE, 
        OBJECT-GROUP,
        NOTIFICATION-GROUP
                FROM SNMPv2-CONF
        DisplayString,
        TruthValue
                FROM SNMPv2-TC 
        CLDot11Band,
        CLDot11ChannelBandwidth
                FROM CISCO-LWAPP-TC-MIB
        ciscoMgmt
                FROM CISCO-SMI;


--********************************************************************
--*  MODULE IDENTITY
--********************************************************************

ciscoLwappDot11MIB   MODULE-IDENTITY
        LAST-UPDATED   "200701040000Z"
        ORGANIZATION   "Cisco Systems Inc."
        CONTACT-INFO  
               "        Cisco Systems,
                        Customer Service
                Postal: 170 West Tasman Drive
                        San Jose, CA  95134
                        USA
                   Tel: +1 800 553-NETS

                 Email: cs-wnbu-snmp@cisco.com"

        DESCRIPTION             
                "This MIB is intended to be implemented on all those
                devices operating as Central controllers, that
                terminate the Light Weight Access Point Protocol
                tunnel from Cisco Light-weight LWAPP Access Points.

                This MIB provides the information about the
                operational parameters of the 802.11 networks.
                References about specific type of 802.11 flavors like
                802.11a/b/g or 802.11n will be made whereever required
                to indicate that the respective parameters are
                applicable only to that particular type of 802.11
                networks.

                The relationship between CC and the LWAPP APs
                can be depicted as follows:

                      +......+     +......+     +......+
                      +      +     +      +     +      +
                      +  CC  +     +  CC  +     +  CC  +
                      +      +     +      +     +      +
                      +......+     +......+     +......+
                        ..            .             .
                        ..            .             .
                       .  .            .             .
                      .    .            .             .
                     .      .            .             .
                    .        .            .             .
                +......+ +......+     +......+      +......+
                +      + +      +     +      +      +      +
                +  AP  + +  AP  +     +  AP  +      +  AP  +
                +      + +      +     +      +      +      +
                +......+ +......+     +......+      +......+
                           .              .             .
                         .  .              .             .
                        .    .              .             .
                       .      .              .             .
                      .        .              .             .
                   +......+ +......+     +......+      +......+
                   +      + +      +     +      +      +      +
                   +  MN  + +  MN  +     +  MN  +      +  MN  +
                   +      + +      +     +      +      +      +
                   +......+ +......+     +......+      +......+


                The LWAPP tunnel exists between the controller and
                the APs.  The MNs communicate with the APs through
                the protocol defined by the 802.11 standard.

                LWAPP APs, upon bootup, discover and join one of the
                controllers and the controller pushes the configuration,
                that includes the WLAN parameters, to the LWAPP APs.
                The APs then encapsulate all the 802.11 frames from
                wireless clients inside LWAPP frames and forward
                the LWAPP frames to the controller.

                                   GLOSSARY

                Access Point ( AP )

                An entity that contains an 802.11 medium access
                control ( MAC ) and physical layer ( PHY ) interface
                and provides access to the distribution services via
                the wireless medium for associated clients.  

                LWAPP APs encapsulate all the 802.11 frames in
                LWAPP frames and sends them to the controller to which
                it is logically connected.

                Gratuitous Probe Response (GPR)

                The Gratuitous Probe Response feature aids in conserving
                battery power of WLAN-enabled cell phones by providing
                a high rate packet on the order of tens of milliseconds
                such that these kind of phones can wake up and wait at
                predefined intervals, to reduce battery power.  The 
                GPR packet is transmitted from the AP at a predefined
                time interval.
                 

                Light Weight Access Point Protocol ( LWAPP )

                This is a generic protocol that defines the 
                communication between the Access Points and the
                Central Controller. 

                Mobile Node ( MN )

                A roaming 802.11 wireless device in a wireless
                network associated with an access point. Mobile Node 
                and client are used interchangeably. 

                TU

                A measurement of time in units of 1024 microseconds.

                802.11n

                802.11n builds upon previous 802.11 standards by adding MIMO 
                (multiple-input multiple-output). MIMO uses multiple 
                transmitter and receiver antennas to allow for increased data 
                throughput through spatial multiplexing and increased range .

 
                A-MPDU
 
                An aggregated format that consists of several MAC
                Protocol Data Units being aggregated and transmitted
                in one PHY Service Data Unit.
 
                A-MSDU
 
                An aggregated format that consists of several MAC
                Service Data Units being aggregated and transmitted
                in one MAC Protocol Data Unit.

                Reduced Inter-Frame Space ( RIFS )
 
                A time interval between multiple transmissions of a
                single transmitter used to reduce overhead and
                increase network efficiency.

                Modulation and Coding Scheme ( MCS )

                This is a value that determines the modulation, coding and
                number of spatial channels.  Each scheme specifies the       
                modulation technique, coding rate , number of spatial
                streams  etc and the corresponding data rate.

                Guard Interval

                Guard intervals are used to ensure that distinct 
                transmissions do not interfere with one another. 
                The purpose of the guard interval is to introduce 
                immunity to propagation delays, echoes and 
                reflections, to which digital data is normally 
                very sensitive.

                Media Access Control ( MAC )

                The Media Access Control Layer is one of two sublayers 
                that make up the Data Link Layer.  The MAC layer is 
                responsible for moving data packets to and from one 
                Network Interface Card (NIC) to another across a shared 
                channel.


                REFERENCE
 
                [1] Wireless LAN Medium Access Control ( MAC ) and
                    Physical Layer ( PHY ) Specifications.

                [2] Draft-obara-Capwap-lwapp-00.txt, IETF Light
                    Weight Access Point Protocol.

                [3] Enhanced Wireless Consortium MAC Specification,
                    v1.24.

                [4] Enhanced Wireless Consortium PHY Specification,
                    v1.27."
        REVISION      "200908240000Z"
        DESCRIPTION
                "Added cldLoadBalancing and cldBandSelect."
  
        REVISION      "200701040000Z"
        DESCRIPTION
                "Initial version of this MIB module. "
        ::= { ciscoMgmt 612 } 
        
ciscoLwappDot11MIBNotifs  OBJECT IDENTIFIER ::= { ciscoLwappDot11MIB 0 }
ciscoLwappDot11MIBObjects OBJECT IDENTIFIER ::= { ciscoLwappDot11MIB 1 }
ciscoLwappDot11MIBConform OBJECT IDENTIFIER ::= { ciscoLwappDot11MIB 2 }

cldConfig OBJECT IDENTIFIER ::= { ciscoLwappDot11MIBObjects 1 }
cldStatus OBJECT IDENTIFIER ::= { ciscoLwappDot11MIBObjects 2 }

--********************************************************************
--*    High Throughput MAc Operations table
--********************************************************************
cldHtMacOperationsTable OBJECT-TYPE
        SYNTAX     SEQUENCE OF CldHtMacOperationsEntry
        MAX-ACCESS not-accessible
        STATUS     current
        DESCRIPTION
                "This table represents the operational parameters
                 at the MAC layer for the 802.11n networks managed 
                 through the controller. An agent adds an entry to 
                 this table for every 802.11n band on startup."
        ::= { cldConfig 1 }

cldHtMacOperationsEntry OBJECT-TYPE
        SYNTAX     CldHtMacOperationsEntry
        MAX-ACCESS not-accessible
        STATUS     current
        DESCRIPTION
                "Each entry represents the operational parameters 
                 at the MAC layer for 802.11n networks."
        INDEX { cldHtDot11nBand }
        ::= { cldHtMacOperationsTable 1 }

CldHtMacOperationsEntry ::=
        SEQUENCE {
                cldHtDot11nBand                INTEGER,
                cldHtDot11nChannelBandwidth    INTEGER,
                cldHtDot11nRifsEnable          TruthValue,
                cldHtDot11nAmsduEnable         TruthValue,
                cldHtDot11nAmpduEnable         TruthValue,
                cldHtDot11nGuardIntervalEnable TruthValue,
                cldHtDot11nEnable              TruthValue
        }

cldHtDot11nBand OBJECT-TYPE
        SYNTAX CLDot11Band
        MAX-ACCESS not-accessible
        STATUS current
        DESCRIPTION
            "This object identifies the 802.11n band the parameters 
             correspond to."
        ::= { cldHtMacOperationsEntry 1 }

cldHtDot11nChannelBandwidth OBJECT-TYPE
        SYNTAX CLDot11ChannelBandwidth 
        MAX-ACCESS read-write
        STATUS current
        DESCRIPTION
             "This object represents the channel bandwidth for 
              the 802.11n networks in the particular band."
        DEFVAL  { twenty }
        ::= { cldHtMacOperationsEntry 2 }

cldHtDot11nRifsEnable OBJECT-TYPE
        SYNTAX TruthValue
        MAX-ACCESS read-write
        STATUS current
        DESCRIPTION
             "This object is used to indicate the support for RIFS on 
              this band. A value of 'true' indicates that RIFS is 
              enabled for this band. A value of 'false' indicates that 
              RIFS is disabled for this band." 
        DEFVAL  { true }
        ::= { cldHtMacOperationsEntry 3 }

cldHtDot11nAmsduEnable OBJECT-TYPE
        SYNTAX TruthValue
        MAX-ACCESS read-write
        STATUS current
        DESCRIPTION
             "This object is used to indicate the support for 802.11n 
               A-MSDU on this band. A value of 'true' indicates that 
               A-MSDU is enabled for this band. A value of 'false' 
               indicates that A-MSDU is disabled for this band." 
        DEFVAL  { true }
        ::= { cldHtMacOperationsEntry 4 }

cldHtDot11nAmpduEnable OBJECT-TYPE
        SYNTAX TruthValue
        MAX-ACCESS read-write
        STATUS current
        DESCRIPTION
             "This object is used to indicate the support for 802.11n 
              A-MPDU on this band. A value of 'true' indicates that 
              A-MPDU is enabled for this band. A value of 'false' 
              indicates that A-MPDU is disabled for this band." 
        DEFVAL  { true }
        ::= { cldHtMacOperationsEntry 5 }

cldHtDot11nGuardIntervalEnable OBJECT-TYPE
        SYNTAX TruthValue
        MAX-ACCESS read-write
        STATUS current
        DESCRIPTION
             "This object is used to indicate the support for 802.11n 
              guard interval on this band. A value of 'true' indicates 
              that guard interval is enabled for this band. A value of 
              'false' indicates that guard interval is disabled for this 
              band." 
        DEFVAL  { true }
        ::= { cldHtMacOperationsEntry 6 }

cldHtDot11nEnable OBJECT-TYPE
        SYNTAX TruthValue
        MAX-ACCESS read-write
        STATUS current
        DESCRIPTION
            "This object is used to enable the controller to manage 
             802.11n networks. A value of 'true' means the 802.11n 
             network is enabled. A value of 'false' means the 802.11n
             network is disabled."
        DEFVAL  { true }
        ::= { cldHtMacOperationsEntry 7 }

--********************************************************************
--*    Configuration for parameters
--********************************************************************
cldMultipleCountryCode OBJECT-TYPE
        SYNTAX DisplayString (SIZE(1..255))
        MAX-ACCESS read-write
        STATUS     current
        DESCRIPTION
                "This object represents the country in which the
                controller is operating. Multiple countries can be set.
                The countries are displayed using a 3 letter code 
                for each country separated by a comma."
        ::= { cldConfig 2 }

cldRegulatoryDomain OBJECT-TYPE
        SYNTAX DisplayString (SIZE(1..255))
        MAX-ACCESS read-only
        STATUS current
        DESCRIPTION
                   "ThiS object represents the regulatory domain for 
                    the controller."
        ::= { cldConfig 3 }

--********************************************************************
--*    MCS table
--********************************************************************
cld11nMcsTable OBJECT-TYPE
        SYNTAX     SEQUENCE OF Cld11nMcsEntry
        MAX-ACCESS not-accessible
        STATUS     current
        DESCRIPTION
                "This table lists the MCS data rates used on the
                 802.11n networks managed by this controller. 
                 All entries are added by the controller at startup."
        ::= { cldConfig 4 }

cld11nMcsEntry OBJECT-TYPE
        SYNTAX     Cld11nMcsEntry
        MAX-ACCESS not-accessible
        STATUS     current
        DESCRIPTION
                "An entry in this table corresponds to a particular 
                 band identified by cld11nMcsBand and for a given index
                 identified by cld11nMcsDataRateIndex."
        INDEX { cld11nMcsBand, cld11nMcsDataRateIndex }
        ::= { cld11nMcsTable 1 }

Cld11nMcsEntry ::=
        SEQUENCE {
                cld11nMcsBand                  INTEGER,
                cld11nMcsDataRateIndex         Unsigned32,
                cld11nMcsDataRate              Unsigned32,
                cld11nMcsSupportEnable         TruthValue
        }

cld11nMcsBand OBJECT-TYPE
        SYNTAX CLDot11Band
        MAX-ACCESS not-accessible
        STATUS current
        DESCRIPTION
                   "This object identifies the 802.11n band to which 
                    the data rate is applicable."
        ::= { cld11nMcsEntry 1 }

cld11nMcsDataRateIndex OBJECT-TYPE
        SYNTAX Unsigned32 (1..256)
        MAX-ACCESS not-accessible
        STATUS current
        DESCRIPTION
                   "This object uniquely identifies the data rate 
                    for a particular band."
        ::= { cld11nMcsEntry 2 }

cld11nMcsDataRate OBJECT-TYPE
        SYNTAX Unsigned32 
        MAX-ACCESS read-only
        STATUS current
        DESCRIPTION
                   "The object represents the data rate value for this 
                    band." 
        ::= { cld11nMcsEntry 3 }

cld11nMcsSupportEnable OBJECT-TYPE
        SYNTAX TruthValue
        MAX-ACCESS read-write
        STATUS current
        DESCRIPTION
                   "This object is used to enable or disable the data 
                    rate.  When this object is set to 'true' the MCS 
                    support is enabled. When this object is set 
                    to 'false' the MCS support is disabled.." 
        DEFVAL  { true }
        ::= { cld11nMcsEntry 4 }


--*****************************
--LOAD BALANCING CONFIGURATION
--*****************************     
cldLoadBalancing OBJECT IDENTIFIER ::= {cldConfig 8}

cldLoadBalancingMode    OBJECT-TYPE
		SYNTAX      INTEGER {
						enable(1),
						disable(2)
					}
		MAX-ACCESS	read-write
		STATUS		deprecated
		DESCRIPTION	
             "This object specifies the mode of Load Balancing.
              Value of 1(enable) will enable the Load Balancing
              and value of 2(disable) will disable it.

              If Load balancing is enable and client tries to 
              associate any overloaded AP, association rejection 
              will be sent to client from AP.
              
              Global configuration of Load Balancing is now removed.
              Use cLWlanLoadBalancingEnable to configure it per WLAN."
		DEFVAL	    { disable }
		::= { cldLoadBalancing 1 }

cldLoadBalancingWindowSize	OBJECT-TYPE
        SYNTAX		Integer32 (0..20)
		MAX-ACCESS	read-write
		STATUS		current
		DESCRIPTION
            "This object specifies the threshold for the difference
             between number of clients a given AP can have and client
             count of the AP having minimum number of clients in the
             setup. 
             
             For example, suppose in a network setup there are three
             APs are connected to Controller, say AP1, AP2 and AP3.
             AP1 have 2 clients, AP2 have 3 and AP3 have 4 clients.
             Here AP1 have minimum number of clients i.e. 2. Suppose
             window size is configured as 2. So every AP can have
             2+2=4 clients. So every 5th client will be load balanced.
             
             So, if any client tries to join AP3, denial will be sent
             from AP3. For a client denial will be send only for 
             cldLoadBalancingDenialCount number of time."
             
		DEFVAL		{ 5 }
		::= { cldLoadBalancing 2 }
		
cldLoadBalancingDenialCount	OBJECT-TYPE
		SYNTAX		Integer32 (1..10)
		MAX-ACCESS	read-write
		STATUS		current
		DESCRIPTION
            "This object specifies maximum number of association
             rejection AP will sent to a client for a given sequence
             of association.
             
             When a client tries to associate on wireless network, it 
             send association request to AP. If AP is overloaded and
             load balancing is enable on controller, AP will send a 
             denial to association request. If there are no other AP
             in the vicinity of client, it will try to associate same
             AP again. So to restrict the number of denial sent from
             AP cldLoadBalancingDenialCount is defined. After maximum
             denial count is reached client will be able to associate.
             
             Association atempts on an AP from any client before 
             associating any AP is called as sequence of assoociation."
             
		DEFVAL		{ 3 }
		::= { cldLoadBalancing 3 }

--**************************
--BAND SELECT CONFIGURATION
--**************************
cldBandSelect OBJECT IDENTIFIER ::= {cldConfig 9}

cldBandSelectMode	OBJECT-TYPE
		SYNTAX		INTEGER {
						enable(1),
						disable(2)
					    }
		MAX-ACCESS	read-write
		STATUS		deprecated
		DESCRIPTION	
            "This object specifies the mode of Band Select.
             The value of 1(enable) will enable the band select
             and value of 2(disable) will disable it.
             
             If Band Select is enable AP suppresses probe response 
             to new clients. AP will suppress probe request coming 
             only on 2.4 GHz radio.
             
             Global configuration of Band Select is now removed.
             Use cLWlanBandSelectEnable to configure it per WLAN."
		DEFVAL		{ disable }
		::= { cldBandSelect 1 }

cldBandSelectCycleCount			OBJECT-TYPE
		SYNTAX		Integer32 (1..10)
		MAX-ACCESS	read-write
		STATUS		current
		DESCRIPTION	
            "This object specifies band select probe cycle count.
             Suppressed clients and corresponding suppression count 
             are recorded in a suppression table. AP will suppress 
             probe request of a client till value of cycle count. 
             AP will increment cycle counter when a client scan
             a channel on 2.4GHz band after any time greater than 
             cldBandSelectCycleThreshold.
             When a client cycle count is reached and if client still
             sends a probe request then AP will respond to it by probe
             response.
             
             For example, let's say, we assume at minimum, a client
             will stay in a channel for 5 milliseconds and there are
             11 channels. If the client scans channel 1 and then the
             other 10 channels, there should be at least a gap of 10x5
             milliseconds between the last time AP hears the client
             probe and the latest one. AP only increments the count if
             the difference of time between the latest and the last 
             probe is more than 50 milliseconds."
		DEFVAL		{ 3 }
		::= { cldBandSelect 2 }

cldBandSelectCycleThreshold		OBJECT-TYPE
		SYNTAX	    Integer32 (1..1000)
		UNITS		"milliseconds"
		MAX-ACCESS	read-write
		STATUS		current
		DESCRIPTION	
            "This object specifies time threshold for a new scanning
             cycle period. Client cycle counter will increment only
             if client scans same channel after any time after this
             value.
             
             For example, if a client is scanning a channel after 
             every 150 milliseconds and cycle threshold value is 
             configures as 200, then cycle count will be incremented
             after 300 seconds. But if client is scanning after every
             250 milliseconds, then cycle count will be incremented 
             after 250 milliseconds."
		DEFVAL		{ 200 }
		::= { cldBandSelect 3 }

cldBandSelectAgeOutSuppression	OBJECT-TYPE
		SYNTAX	    Integer32(10..200)
		UNITS		"seconds"
		MAX-ACCESS	read-write
		STATUS		current
		DESCRIPTION	
                "Suppressed client are recorded in a suppression table.
                 This object specifies age out period after which entry
                 of client will be removed.
                 All entries will stay in the table until it is aged
                 out or is replaced when table is full. If table is
                 full, and there is no space for new client then AP 
                 will replaced the oldest entry on the table that it
                 had responded already. If there as no empty slot in
                 the table, AP has to respond to all the new clients
                 until space starts getting available."
		DEFVAL		{ 20 }
		::= { cldBandSelect 4 }

cldBandSelectAgeOutDualBand		OBJECT-TYPE
		SYNTAX	    Integer32 (10..300)
		UNITS		"seconds"
		MAX-ACCESS	read-write
		STATUS		current
		DESCRIPTION
                "When AP sees probe request from any client in both 
                 2.4GHz and 5GHz band AP will know that client is 
                 capable of operating on both band. Dual band capable
                 clients are recorded in a dual band client table. 
                 This record are kept to make sure 5GHz capable clients
                 should join 5GHz band only. 
                 Entries in the table will be age out to make space for
                 new entries. This objects specifies age out period 
                 after which client entry will be removed.
                 
                 The AP will not respond to the dual band client's 
                 2.4GHz probe until is removed from the dual band 
                 client table. AP fills the dual band table in the
                 following order until it is full:
                 1) clients with 5GHz probe that have associated to 
                    2.4GHz.
                 2)	clients with 5GHz probe that also have 2.4GHz
                    probes.
                 3) clients with just 5GHz probe detected and 5GHz
                    association."
		DEFVAL		{ 60 }
		::= { cldBandSelect 5 }

cldBandSelectClientRssi			OBJECT-TYPE
		SYNTAX		Integer32 (-90..-20)
		UNITS		"dBm"
		MAX-ACCESS	read-write
		STATUS		current
		DESCRIPTION	
                "This object specifies minimum client RSSI threshold.
                 Client having RSSI below this value will not be 
                 recorded in suppressed client table.
                 This configuration filter out far away clients with
                 low signal strength. This will limit the number of
                 client on the table to a reasonable amount."
		DEFVAL		{ -80 }
		::= { cldBandSelect 6 }        

        
-- ********************************************************************
-- Channel table for all  Country codes 
-- ********************************************************************
cldCountryTable OBJECT-TYPE
        SYNTAX     SEQUENCE OF CldCountryEntry
        MAX-ACCESS not-accessible
        STATUS     current
        DESCRIPTION
                "This table provides the list of countries and the
                 network parameters specific to those respective 
                 countries the 802.11 networks managed by this controller 
                 can operate in. ALll entries are added by the controller
                 at startup."
        ::= { cldStatus 1 }

cldCountryEntry OBJECT-TYPE
        SYNTAX     CldCountryEntry
        MAX-ACCESS not-accessible
        STATUS     current
        DESCRIPTION
                "A conceptual row in cldCountryTable. There is an entry in
                 this table for each country available at the
                 agent, as identified by a value of cldCountryCode. Each
                 entry also displays the corresponding channels supported
                 by the cldCountryCode."
        INDEX { cldCountryCode }
        ::= { cldCountryTable 1 }

CldCountryEntry ::=
        SEQUENCE {
                cldCountryCode                 DisplayString,
                cldCountryName                 DisplayString,
                cldCountryDot11aChannels       DisplayString,
                cldCountryDot11bChannels       DisplayString,
                cldCountryDot11aDcaChannels    DisplayString,
                cldCountryDot11bDcaChannels    DisplayString
        }

cldCountryCode OBJECT-TYPE
        SYNTAX     DisplayString
        MAX-ACCESS not-accessible
        STATUS     current
        DESCRIPTION
                "This object identifies the country for this entry. 
                 The 3 letter country code for this index."
        ::= { cldCountryEntry 1 }

cldCountryName OBJECT-TYPE
        SYNTAX     DisplayString
        MAX-ACCESS read-only
        STATUS     current
        DESCRIPTION
                "The country name for this index."
        ::= { cldCountryEntry 2 }

cldCountryDot11aChannels OBJECT-TYPE
        SYNTAX     DisplayString
        MAX-ACCESS read-only
        STATUS     current
        DESCRIPTION
                "The 802.11a channels separated by comma."
        ::= { cldCountryEntry 3 }

cldCountryDot11bChannels OBJECT-TYPE
        SYNTAX     DisplayString
        MAX-ACCESS read-only
        STATUS     current
        DESCRIPTION
                "The 802.11b channels separated by comma."
        ::= { cldCountryEntry 4 }

cldCountryDot11aDcaChannels OBJECT-TYPE
        SYNTAX     DisplayString
        MAX-ACCESS read-only
        STATUS     current
        DESCRIPTION
                "The 802.11a DCA channels separated by comma."
        ::= { cldCountryEntry 5 }

cldCountryDot11bDcaChannels OBJECT-TYPE
        SYNTAX     DisplayString
        MAX-ACCESS read-only
        STATUS     current
        DESCRIPTION
                "The 802.11b DCA channels separated by comma."
        ::= { cldCountryEntry 6 }

--******************************************************************** 
--*    NOTIFICATION Control objects
--********************************************************************
cldCountryChangeNotifEnable OBJECT-TYPE
        SYNTAX     TruthValue
        MAX-ACCESS read-write
        STATUS     current
        DESCRIPTION
                "This object is used to control the generation of
                ciscoLwappDot11CountryChangeNotif notification.

                A value of 'true' indicates that the agent generates
                ciscoLwappDot11CountryChangeNotif notification.

                A value of 'false' indicates that the agent doesn't
                generate ciscoLwappDot11CountryChangeNotif notification."
        DEFVAL  { true }
        ::= { cldConfig 7 }


-- ********************************************************************
-- Country Notifications 
-- ********************************************************************
ciscoLwappDot11CountryChangeNotif NOTIFICATION-TYPE
    OBJECTS { cldMultipleCountryCode }
    STATUS current
    DESCRIPTION
        "This notification is generated by the controller when the
         country of operation of 802.11 networks is changed 
         by the administrator. The new country code will be sent in 
         this notification."
    ::= { ciscoLwappDot11MIBNotifs 1 }


--********************************************************************
--*    Units of conformance  
--********************************************************************
ciscoLwappDot11MIBCompliances OBJECT IDENTIFIER
        ::= { ciscoLwappDot11MIBConform 1 }

ciscoLwappDot11MIBGroups OBJECT IDENTIFIER
        ::= { ciscoLwappDot11MIBConform 2 }
-- STATUS deprecated by ciscoLwappDot11MIBComplianceRev1 
ciscoLwappDot11MIBCompliance MODULE-COMPLIANCE
        STATUS     deprecated
        DESCRIPTION
                "The compliance statement for the SNMP entities that
                implement the ciscoLwappDot11MIB module. "
        MODULE MANDATORY-GROUPS {
                ciscoLwappDot11MIBMacOperGroup
        }
        ::= { ciscoLwappDot11MIBCompliances 1 }

-- Added since last MIB approval
ciscoLwappDot11MIBComplianceRev1 MODULE-COMPLIANCE
        STATUS     current
        DESCRIPTION
                "The compliance statement for the SNMP entities that
                implement the ciscoLwappDot11MIB module. "
        MODULE MANDATORY-GROUPS {
                ciscoLwappDot11MIBMacOperGroup,
                ciscoLwappDot11MIBConfigGroup1,
                ciscoLwappDot11MIBNotifsGroup,
                ciscoLwappDot11MIBStatusGroup,
                ciscoLwappDot11MIBConfigGroup2
        }
        ::= { ciscoLwappDot11MIBCompliances 2 }

ciscoLwappDot11MIBMacOperGroup OBJECT-GROUP
        OBJECTS {
                    cldHtDot11nChannelBandwidth,
                    cldHtDot11nRifsEnable,
                    cldHtDot11nAmsduEnable,
                    cldHtDot11nAmpduEnable,
                    cldHtDot11nGuardIntervalEnable
        }
        STATUS     current
        DESCRIPTION
                "This collection of objects represents the 
                operational parameters at the MAC layer
                for the 802.11n networks."
        ::= { ciscoLwappDot11MIBGroups 1 }

ciscoLwappDot11MIBConfigGroup1 OBJECT-GROUP
        OBJECTS {
                    cldHtDot11nEnable, 
                    cldMultipleCountryCode,
                    cldRegulatoryDomain,
                    cld11nMcsDataRate, 
                    cld11nMcsSupportEnable, 
                    cldCountryChangeNotifEnable 
        }
        STATUS     current
        DESCRIPTION
                "This collection of objects specifies the configuration
                parameters of 802.11i networks."
        ::= { ciscoLwappDot11MIBGroups 2 }


ciscoLwappDot11MIBNotifsGroup NOTIFICATION-GROUP
        NOTIFICATIONS {
                        ciscoLwappDot11CountryChangeNotif
        }
        STATUS     current
        DESCRIPTION
                "This collection of objects specifies the
                 notifications generated by the controller."
        ::= { ciscoLwappDot11MIBGroups 3 }

ciscoLwappDot11MIBStatusGroup OBJECT-GROUP
        OBJECTS {
                    cldCountryName,           
                    cldCountryDot11aChannels, 
                    cldCountryDot11bChannels, 
                    cldCountryDot11aDcaChannels,
                    cldCountryDot11bDcaChannels
        }
        STATUS     current
        DESCRIPTION
                "This collection of objects specifies the
                notification objects for 802.11."
        ::= { ciscoLwappDot11MIBGroups 4 }

ciscoLwappDot11MIBConfigGroup2 OBJECT-GROUP
        OBJECTS {
                    cldLoadBalancingMode,
                    cldLoadBalancingWindowSize,
                    cldLoadBalancingDenialCount,
                    cldBandSelectMode,
                    cldBandSelectCycleCount,
                    cldBandSelectCycleThreshold,
                    cldBandSelectAgeOutSuppression,
                    cldBandSelectAgeOutDualBand,
                    cldBandSelectClientRssi
                    
        }
        STATUS     current
        DESCRIPTION
                "This collection of objects specifies the Load 
                 Balancing and Band Select configuration parameters
                 of 802.11 networks."
        ::= { ciscoLwappDot11MIBGroups 5 }

END
