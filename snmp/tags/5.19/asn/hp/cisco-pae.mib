-- $Id: cisco-pae.mib,v 1.1 2005/04/25 20:29:47 kallio Exp $
-- $Source: /var/cvs/nimbus/src/mibs/cisco-pae.mib,v $
-- *****************************************************************
-- CISCO-PAE-MIB: CISCO private MIB for IEEE 801.1x
--
-- September 2001, Binh P Le
--
-- Copyright (c) 2001-2002,2003 by cisco Systems, Inc.
-- All rights reserved.
-- *****************************************************************
-- $Log: cisco-pae.mib,v $
-- Revision 1.1  2005/04/25 20:29:47  kallio
-- Add new cisco mibs
--
-- Revision 1.1  2005/03/14 16:30:52  aminchew
-- Initial revision
-- Revision 1.1.2.1  2005/02/08 01:45:10  bruceg
-- CGESM_12_2_25
--
-- *****************************************************************
-- $Endlog$
--

CISCO-PAE-MIB DEFINITIONS ::= BEGIN

IMPORTS 
    OBJECT-TYPE,
    MODULE-IDENTITY, Unsigned32
        FROM SNMPv2-SMI

    TruthValue 
        FROM SNMPv2-TC

    MODULE-COMPLIANCE,
    OBJECT-GROUP
        FROM SNMPv2-CONF

    dot1xPaePortEntry
        FROM IEEE8021-PAE-MIB

    VlanIndex 
        FROM CISCO-VTP-MIB

    ciscoMgmt
        FROM CISCO-SMI;
    
ciscoPaeMIB MODULE-IDENTITY
    LAST-UPDATED "200302260000Z" 
    ORGANIZATION "Cisco System, Inc."
    CONTACT-INFO 
            "         Cisco Systems
                      Customer Service

              Postal: 170 W Tasman Drive
                      San Jose, CA  95134
                      USA

                 Tel: +1 800 553-NETS

        E-mail: cs-wbu@cisco.com"
    DESCRIPTION 
        "Cisco Port Access Entity (PAE) module for managing 
        IEEE Std 802.1x.

        This MIB provides Port Access Entity information that are 
        either excluded by IEEE Std 802.1x (IEEE8021-PAE-MIB) or
        specific to Cisco products."
    REVISION    "200302260000Z"
    DESCRIPTION
        "Add SNMP support for per-port Guest Vlan and shutdown 
         timer features. The object cpaeGuestVlanId and group 
         cpaeGuestVlanGroup have been deprecated. The objects
         cpaeGuestVlanNumber and cpaeInGuestVlan have been added
         to support per-interface Guest Vlan, cpaeShutdownTimer and
         cpaeShutdownTimerEnabled have been added to support
         shutdown timer features."

    REVISION    "200210160000Z"
    DESCRIPTION
        "Add SNMP support for the Multiple Authentication and
         and Guest Vlan features.
         
         The objects cpaeMultipleHost has been deprecated, and 
         cpaePortMode has been added to cpaePortTable to support
         for Multiple Authentication feature. The object 
         cpaeGuestVlanId has been added to support for Guest Vlan
         feature."


    REVISION    "200105241016Z"
    DESCRIPTION
        "Initial version of this MIB module."

    ::= {ciscoMgmt 220}

cpaeMIBNotification OBJECT IDENTIFIER ::= {ciscoPaeMIB 0}
cpaeMIBObject OBJECT IDENTIFIER ::= {ciscoPaeMIB 1}

cpaePortTable OBJECT-TYPE
    SYNTAX        SEQUENCE OF CpaePortEntry
    MAX-ACCESS    not-accessible
    STATUS        current
    DESCRIPTION
        "A table of system level information for each port
        supported by the Port Access Entity.  An entry 
        appears in this table for each PAE port of this system.
        This table contains additional objects for the
        dot1xPaePortTable."
    REFERENCE
        "IEEE 802.1x Subclause 9.6.1"
    ::= {cpaeMIBObject 1}

cpaePortEntry OBJECT-TYPE
    SYNTAX        CpaePortEntry
    MAX-ACCESS    not-accessible
    STATUS        current
    DESCRIPTION    
        "An entry containing additional management information
        applicable to a particular PAE port."
    AUGMENTS    {dot1xPaePortEntry}
    ::= {cpaePortTable 1}


CpaePortEntry ::= SEQUENCE {
    cpaeMultipleHost          TruthValue,
    cpaePortMode              INTEGER,
    cpaeGuestVlanNumber       VlanIndex,
    cpaeInGuestVlan           TruthValue,
    cpaeShutdownTimerEnabled  TruthValue
}

cpaeMultipleHost OBJECT-TYPE
    SYNTAX        TruthValue
    MAX-ACCESS    read-write
    STATUS        deprecated
    DESCRIPTION
        "Specifies whether the port allows multiple-host connection
        or not."
    ::= {cpaePortEntry 1}

cpaePortMode OBJECT-TYPE
    SYNTAX        INTEGER {
                     singleHost(1),
                     multiHost(2),
                     multiAuth(3)
                  }
    MAX-ACCESS    read-write
    STATUS        current
    DESCRIPTION
        "Specifies the current mode of dot1x operation on the port.
            - singleHost(1): port allows one host to connect and
                 authenticate.
            - multiHost(2) : port allows multiple hosts to connect.
                 Once a host is authenticated, all remaining hosts
                 are also authorized.
            - multiAuth(3) : port allows multiple hosts to connect.
                 Authorized hosts will be secured by Port Security
                 feature. The number of hosts that can be authorized
                 is restricted by the maximum hosts allowed by Port
                 Security, which is controlled by the object
                 portSecurityMaxSrcAddr in portSecurityTable."
    REFERENCE
        "CISCO-STACK-MIB, portSecurityTable"
    ::= {cpaePortEntry 2}

cpaeGuestVlanNumber OBJECT-TYPE
    SYNTAX       VlanIndex
    MAX-ACCESS   read-write
    STATUS       current
    DESCRIPTION
        "Specifies the Guest Vlan of the interface. An interface in
         singleHost(1) mode will be moved to its Guest Vlan if its
         access is unsucessfully authenticated. A value of zero
         indicates no Guest Vlan configured for the interface."
    ::= {cpaePortEntry 3}


cpaeInGuestVlan OBJECT-TYPE
    SYNTAX       TruthValue
    MAX-ACCESS   read-only
    STATUS       current
    DESCRIPTION
        "Indicates whether the interface is in its Guest Vlan or
         not."
    ::= {cpaePortEntry 4}

cpaeShutdownTimerEnabled OBJECT-TYPE
    SYNTAX       TruthValue
    MAX-ACCESS   read-write
    STATUS       current
    DESCRIPTION
        "Specifies whether shutdown timer is enabled on the 
         interface."
    ::= {cpaePortEntry 5}

cpaeGuestVlanId OBJECT-TYPE
    SYNTAX       VlanIndex
    MAX-ACCESS   read-write
    STATUS       deprecated
    DESCRIPTION
        "Specifies the Guest Vlan of the system. An interface in
         singleHost(1) mode will be moved to Guest Vlan if its 
         access is unsuccessfully authenticated. A value of zero
         indicates no Guest Vlan configured in the system."
    ::= {cpaeMIBObject 2}

cpaeShutdownTimer OBJECT-TYPE
    SYNTAX       Unsigned32 (0..65635)
    MAX-ACCESS   read-write
    STATUS       current
    DESCRIPTION
        "Specifies the shutdown timer value to enable an interface
         automatically in case it is shutdown due to security violation.
         If both dot1x and port security are enabled on the interface,
         the port security shutdown timer will take precedence over
         the dot1x shutdown timer. Dot1x shutdown timer is applicable
         only when cpaeShutdownTimerEnabled is 'true', and port 
         security feature is not enabled on the interface. Interfaces
         will not be enabled automatically after security violation if
         the value of cpaeShutdownTimer is zero."
    ::= {cpaeMIBObject 3}

------------------------------------------
-- Conformance Information
------------------------------------------
cpaeMIBConformance OBJECT IDENTIFIER ::= {ciscoPaeMIB 2}
cpaeMIBCompliances OBJECT IDENTIFIER ::= {cpaeMIBConformance 1}
cpaeMIBGroups OBJECT IDENTIFIER ::= {cpaeMIBConformance 2}

-- Conformance 

cpaeCompliance MODULE-COMPLIANCE
    STATUS     deprecated
    DESCRIPTION
        "The compliance statement."
    MODULE
        MANDATORY-GROUPS {
            cpaeMultipleHostGroup
        }
    ::= {cpaeMIBCompliances 1}

cpaeCompliance2 MODULE-COMPLIANCE
    STATUS     deprecated
    DESCRIPTION
        "The compliance statement for devices that implement
         the CISCO-PAE-MIB."
    MODULE
        MANDATORY-GROUPS {
            cpaePortEntryGroup
        }

    GROUP    cpaeGuestVlanGroup
    DESCRIPTION
        "This group is mandatory in devices running software
         which supports Guest Vlan feature."

    ::= {cpaeMIBCompliances 2}

cpaeCompliance3 MODULE-COMPLIANCE
    STATUS     current
    DESCRIPTION
        "The compliance statement for devices that implement
         the CISCO-PAE-MIB."
    MODULE
        MANDATORY-GROUPS {
            cpaePortEntryGroup
        }

    GROUP    cpaeGuestVlanGroup2
    DESCRIPTION
        "This group is mandatory in devices running software
         which supports per-interface Guest Vlan feature."

    GROUP    cpaeShutdownTimerGroup
    DESCRIPTION
        "This group is mandatory in devices running software
         which support Shutdown Timer feature."
    ::= {cpaeMIBCompliances 3}

-- Units of Conformance

cpaeMultipleHostGroup    OBJECT-GROUP
    OBJECTS {
        cpaeMultipleHost
    }
    STATUS    deprecated
    DESCRIPTION    
        "A collection of objects that provide the multiple 
        host configuration information for a PAE port.  
        These are additional to the IEEE Std 802.1x PAE MIB."
    ::= {cpaeMIBGroups 1}

cpaePortEntryGroup OBJECT-GROUP
    OBJECTS {
        cpaePortMode
    }
    STATUS    current
    DESCRIPTION
        "A collection of objects that provides the port-mode
         configuration for a PAE port."
    ::= {cpaeMIBGroups 2}

cpaeGuestVlanGroup       OBJECT-GROUP
    OBJECTS {
        cpaeGuestVlanId
    }
    STATUS    deprecated
    DESCRIPTION
        "A collection of objects that provides the Guest Vlan
         configuration information for the system."
    ::= {cpaeMIBGroups 3}

cpaeGuestVlanGroup2       OBJECT-GROUP
    OBJECTS {
        cpaeGuestVlanNumber,
        cpaeInGuestVlan
    }
    STATUS    current
    DESCRIPTION
        "A collection of objects that provides the per-interface
         Guest Vlan configuration information for the system."
    ::= {cpaeMIBGroups 4}

cpaeShutdownTimerGroup    OBJECT-GROUP
    OBJECTS {
        cpaeShutdownTimer,
        cpaeShutdownTimerEnabled 
    }
    STATUS    current
    DESCRIPTION
        "A collection of objects that provides the dot1x shutdown
         timer configuration information for the system."
    ::= {cpaeMIBGroups 5}
END
