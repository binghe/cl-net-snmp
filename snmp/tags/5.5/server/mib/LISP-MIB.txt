-- $Id$

LISP-MIB DEFINITIONS ::= BEGIN

IMPORTS
    MODULE-IDENTITY, OBJECT-TYPE, OBJECT-IDENTITY,
    NOTIFICATION-TYPE, enterprises
        FROM SNMPv2-SMI;

lisp MODULE-IDENTITY
    LAST-UPDATED "200807290000Z" -- 29 July 2008
    ORGANIZATION
           "The cl-net-snmp Project
	    http://common-lisp.net/projects/cl-net-snmp"
    CONTACT-INFO
           "Chun Tian (binghe)

            Email: <binghe.lisp@gmail.com>

            Send comments to
              <cl-net-snmp-general@lists.sourceforge.net>"
    DESCRIPTION
           "The MIB module for Lisp."
    REVISION "200809240000Z" -- 24 September 2008
    DESCRIPTION
           "Redefine lispFeatures as a MIB Table, add lispFeatureTable, lispPackageTable"
    REVISION "200807290000Z" -- 29 July 2008
    DESCRIPTION
           "The initial revision of this MIB module."
    ::= { enterprises 31609 }

common-lisp     OBJECT IDENTIFIER ::= { lisp 1 }
scheme          OBJECT IDENTIFIER ::= { lisp 2 }

-- lisp.3+ is for other dialets

lispSystem       OBJECT IDENTIFIER ::= { common-lisp 1 }
lispConstants    OBJECT IDENTIFIER ::= { common-lisp 2 }
lispPackages     OBJECT IDENTIFIER ::= { common-lisp 3 } -- (Small) Utility
lispApplications OBJECT IDENTIFIER ::= { common-lisp 4 } -- (Big) Applications

lispImplementationType OBJECT-TYPE
    SYNTAX      OCTET STRING
    MAX-ACCESS  read-only
    STATUS      current
    DESCRIPTION "(lisp-implementation-type)"
    ::= { lispSystem 1 }

lispImplementationVersion OBJECT-TYPE
    SYNTAX      OCTET STRING
    MAX-ACCESS  read-only
    STATUS      current
    DESCRIPTION "(lisp-implementation-version)"
    ::= { lispSystem 2 }

lispLongSiteName OBJECT-TYPE
    SYNTAX      OCTET STRING
    MAX-ACCESS  read-write
    STATUS      current
    DESCRIPTION "(long-site-name)"
    ::= { lispSystem 3 }

lispShortSiteName OBJECT-TYPE
    SYNTAX      OCTET STRING
    MAX-ACCESS  read-write
    STATUS      current
    DESCRIPTION "(short-site-name)"
    ::= { lispSystem 4 }

lispMachineInstance OBJECT-TYPE
    SYNTAX      OCTET STRING
    MAX-ACCESS  read-only
    STATUS      current
    DESCRIPTION "(machine-instance)"
    ::= { lispSystem 5 }

lispMachineType OBJECT-TYPE
    SYNTAX      OCTET STRING
    MAX-ACCESS  read-only
    STATUS      current
    DESCRIPTION "(machine-type)"
    ::= { lispSystem 6 }

lispMachineVersion OBJECT-TYPE
    SYNTAX      OCTET STRING
    MAX-ACCESS  read-only
    STATUS      current
    DESCRIPTION "(machine-version)"
    ::= { lispSystem 7 }

lispSoftwareType OBJECT-TYPE
    SYNTAX      OCTET STRING
    MAX-ACCESS  read-only
    STATUS      current
    DESCRIPTION "(software-type)"
    ::= { lispSystem 8 }

lispSoftwareVersion OBJECT-TYPE
    SYNTAX      OCTET STRING
    MAX-ACCESS  read-only
    STATUS      current
    DESCRIPTION "(software-version)"
    ::= { lispSystem 9 }

lispInternalRealTime OBJECT-TYPE
    SYNTAX      INTEGER
    MAX-ACCESS  read-only
    STATUS      current
    DESCRIPTION "(get-internal-real-time)"
    ::= { lispSystem 10 }

lispInternalRunTime OBJECT-TYPE
    SYNTAX      INTEGER
    MAX-ACCESS  read-only
    STATUS      current
    DESCRIPTION "(get-internal-run-time)"
    ::= { lispSystem 11 }

lispInternalTimeUnitsPerSecond OBJECT-TYPE
    SYNTAX      INTEGER
    MAX-ACCESS  read-only
    STATUS      current
    DESCRIPTION "internal-time-units-per-second"
    ::= { lispSystem 12 }

lispUniversalTime OBJECT-TYPE
    SYNTAX      INTEGER
    MAX-ACCESS  read-only
    STATUS      current
    DESCRIPTION "(get-universal-time)"
    ::= { lispSystem 13 }

lispFeatureTable OBJECT-TYPE
    SYNTAX      SEQUENCE OF lispFeatureEntry
    MAX-ACCESS  not-accessible
    STATUS      current
    DESCRIPTION "*features*"
    ::= { lispSystem 14 }

lispFeatureEntry OBJECT-TYPE
    SYNTAX     LispFeatureEntry
    MAX-ACCESS not-accessible
    STATUS     current
    DESCRIPTION
            "An entry (conceptual row) in the lispFeatureTable."
    INDEX      { lispFeatureIndex }
    ::= { lispFeatureTable 1 }

LispFeatureEntry ::= SEQUENCE {
    lispFeatureIndex INTEGER,
    lispFeatureName  DisplayString
}

lispFeatureIndex OBJECT-TYPE
    SYNTAX      INTEGER
    MAX-ACCESS  not-accessible
    STATUS      current
    DESCRIPTION
            "The auxiliary variable used for identifying instances
            of the columnar objects in the lispFeatureTable."
    ::= { lispFeatureEntry 1 }

lispFeatureName OBJECT-TYPE
    SYNTAX      DisplayString
    MAX-ACCESS  read-only
    STATUS      current
    DESCRIPTION
            "The string name of each element in *features*."
    ::= { lispFeatureEntry 2 }

lispPackageTable OBJECT-TYPE
    SYNTAX      SEQUENCE OF lispPackageEntry
    MAX-ACCESS  not-accessible
    STATUS      current
    DESCRIPTION "(list-all-packages)"
    ::= { lispSystem 15 }

lispPackageEntry OBJECT-TYPE
    SYNTAX     LispPackageEntry
    MAX-ACCESS not-accessible
    STATUS     current
    DESCRIPTION
            "An entry (conceptual row) in the lispPackageTable."
    INDEX      { lispPackageIndex }
    ::= { lispPackageTable 1 }

LispPackageEntry ::= SEQUENCE {
    lispPackageIndex INTEGER,
    lispPackageName  DisplayString
}

lispPackageIndex OBJECT-TYPE
    SYNTAX      INTEGER
    MAX-ACCESS  not-accessible
    STATUS      current
    DESCRIPTION
            "The auxiliary variable used for identifying instances
            of the columnar objects in the lispPackageTable."
    ::= { lispPackageEntry 1 }

lispPackageName OBJECT-TYPE
    SYNTAX      DisplayString
    MAX-ACCESS  read-only
    STATUS      current
    DESCRIPTION
            "The string name of each element in (list-all-packages)."
    ::= { lispPackageEntry 2 }

lispMostPositiveShortFloat OBJECT-TYPE
    SYNTAX      OCTET STRING
    MAX-ACCESS  read-only
    STATUS      current
    ::= { lispConstants 1 }

lispLeastPositiveShortFloat OBJECT-TYPE
    SYNTAX      OCTET STRING
    MAX-ACCESS  read-only
    STATUS      current
    ::= { lispConstants 2 }

lispLeastPositiveNormalizedShortFloat OBJECT-TYPE
    SYNTAX      OCTET STRING
    MAX-ACCESS  read-only
    STATUS      current
    ::= { lispConstants 3 }

lispMostPositiveDoubleFloat OBJECT-TYPE
    SYNTAX      OCTET STRING
    MAX-ACCESS  read-only
    STATUS      current
    ::= { lispConstants 4 }

lispLeastPositiveDoubleFloat OBJECT-TYPE
    SYNTAX      OCTET STRING
    MAX-ACCESS  read-only
    STATUS      current
    ::= { lispConstants 5 }

lispLeastPositiveNormalizedDoubleFloat OBJECT-TYPE
    SYNTAX      OCTET STRING
    MAX-ACCESS  read-only
    STATUS      current
    ::= { lispConstants 6 }

lispMostPositiveLongFloat OBJECT-TYPE
    SYNTAX      OCTET STRING
    MAX-ACCESS  read-only
    STATUS      current
    ::= { lispConstants 7 }

lispLeastPositiveLongFloat OBJECT-TYPE
    SYNTAX      OCTET STRING
    MAX-ACCESS  read-only
    STATUS      current
    ::= { lispConstants 8 }

lispLeastPositiveNormalizedLongFloat OBJECT-TYPE
    SYNTAX      OCTET STRING
    MAX-ACCESS  read-only
    STATUS      current
    ::= { lispConstants 9 }

lispMostPositiveSingleFloat OBJECT-TYPE
    SYNTAX      OCTET STRING
    MAX-ACCESS  read-only
    STATUS      current
    ::= { lispConstants 10 }

lispLeastPositiveSingleFloat OBJECT-TYPE
    SYNTAX      OCTET STRING
    MAX-ACCESS  read-only
    STATUS      current
    ::= { lispConstants 11 }

lispLeastPositiveNormalizedSingleFloat OBJECT-TYPE
    SYNTAX      OCTET STRING
    MAX-ACCESS  read-only
    STATUS      current
    ::= { lispConstants 12 }

lispMostNegativeShortFloat OBJECT-TYPE
    SYNTAX      OCTET STRING
    MAX-ACCESS  read-only
    STATUS      current
    ::= { lispConstants 13 }

lispLeastNegativeShortFloat OBJECT-TYPE
    SYNTAX      OCTET STRING
    MAX-ACCESS  read-only
    STATUS      current
    ::= { lispConstants 14 }

lispLeastNegativeNormalizedShortFloat OBJECT-TYPE
    SYNTAX      OCTET STRING
    MAX-ACCESS  read-only
    STATUS      current
    ::= { lispConstants 15 }

lispMostNegativeSingleFloat OBJECT-TYPE
    SYNTAX      OCTET STRING
    MAX-ACCESS  read-only
    STATUS      current
    ::= { lispConstants 16 }

lispLeastNegativeSingleFloat OBJECT-TYPE
    SYNTAX      OCTET STRING
    MAX-ACCESS  read-only
    STATUS      current
    ::= { lispConstants 17 }

lispLeastNegativeNormalizedSingleFloat OBJECT-TYPE
    SYNTAX      OCTET STRING
    MAX-ACCESS  read-only
    STATUS      current
    ::= { lispConstants 18 }

lispMostNegativeDoubleFloat OBJECT-TYPE
    SYNTAX      OCTET STRING
    MAX-ACCESS  read-only
    STATUS      current
    ::= { lispConstants 19 }

lispLeastNegativeDoubleFloat OBJECT-TYPE
    SYNTAX      OCTET STRING
    MAX-ACCESS  read-only
    STATUS      current
    ::= { lispConstants 20 }

lispLeastNegativeNormalizedDoubleFloat OBJECT-TYPE
    SYNTAX      OCTET STRING
    MAX-ACCESS  read-only
    STATUS      current
    ::= { lispConstants 21 }

lispMostNegativeLongFloat OBJECT-TYPE
    SYNTAX      OCTET STRING
    MAX-ACCESS  read-only
    STATUS      current
    ::= { lispConstants 22 }

lispLeastNegativeLongFloat OBJECT-TYPE
    SYNTAX      OCTET STRING
    MAX-ACCESS  read-only
    STATUS      current
    ::= { lispConstants 23 }

lispLeastNegativeNormalizedLongFloat OBJECT-TYPE
    SYNTAX      OCTET STRING
    MAX-ACCESS  read-only
    STATUS      current
    ::= { lispConstants 24 }

cl-net-snmp             OBJECT IDENTIFIER ::= { lispPackages 1 }
clNetSnmpObjects        OBJECT IDENTIFIER ::= { cl-net-snmp 1 }
clNetSnmpEnumerations   OBJECT IDENTIFIER ::= { cl-net-snmp 2 }

clNetSnmpAgentOIDs      OBJECT IDENTIFIER ::= { clNetSnmpEnumerations 1 }
clNetSnmpAgent          OBJECT IDENTIFIER ::= { clNetSnmpAgentOIDs 1 }
clNetSnmpAgentLispWorks OBJECT IDENTIFIER ::= { clNetSnmpAgentOIDs 5 }
clNetSnmpAgentCMUCL     OBJECT IDENTIFIER ::= { clNetSnmpAgentOIDs 6 }
clNetSnmpAgentSBCL      OBJECT IDENTIFIER ::= { clNetSnmpAgentOIDs 7 }
clNetSnmpAgentClozure   OBJECT IDENTIFIER ::= { clNetSnmpAgentOIDs 8 }
clNetSnmpAgentAllegroCL OBJECT IDENTIFIER ::= { clNetSnmpAgentOIDs 9 }

END
