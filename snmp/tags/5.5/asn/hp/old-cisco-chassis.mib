-- $Source: /var/cvs/nimbus/src/mibs/old-cisco-chassis.mib,v $
-- *****************************************************************
-- OLD-CISCO-CHASSIS-MIB.my:  Cisco Chassis MIB file
--
--%DNP%  NOTE WELL: The Cisco Assigned Numbers Authority (CANA)
--%DNP%             controls all enumeration assignments in this MIB.
--%DNP%             Do not add, delete, or modify this MIB without
--%DNP%             explicit instructions from the CANA.  Requests for
--%DNP%             new enumeration types should be requested at
--%DNP%             http://wwwin-eng.cisco.com/Eng/IOSTech/CANA_WWW/
--
-- May 1994, Jeffrey T. Johnson
--
-- Copyright (c) 1994-2001, 2002, 2003, 2004 by cisco Systems, Inc.
-- All rights reserved.
--
-- NOTE WELL
-- Starting with IOS 12.0, all objects defined in this mib have been
-- deprecated.  They have been replaces with objects defined in the
-- ENTITY-MIB.my document. Management applications should no longer
-- be examining the objects defined in this document.
-- NOTE WELL
-- 
-- *****************************************************************
-- $Log: old-cisco-chassis.mib,v $
-- Revision 1.1  2005/04/25 20:37:41  kallio
-- New changes from mgmt cd 730
--
-- Revision 1.1  2005/03/14 16:34:10  aminchew
-- Initial revision
-- Revision 1.1.2.1  2005/02/08 01:45:11  bruceg
-- CGESM_12_2_25
--
-- *****************************************************************
-- $Endlog$
--
--%DNP%  FYI:  Lines containing a comment starting with the "Do Not
--%DNP%  Publish" prefix "%DNP%" (such as these) are automagicially
--%DNP%  stripped from MIBS prior to publishing on ftp and cio, and
--%DNP%  should be used for comments intended for cisco engineering
--%DNP%  eyes only, or for new product identifiers that are not yet
--%DNP%  announced.
--
               OLD-CISCO-CHASSIS-MIB DEFINITIONS ::= BEGIN

               IMPORTS
                    TimeTicks
                        FROM RFC1155-SMI
                    OBJECT-TYPE
			FROM RFC-1212
		    TRAP-TYPE			--%DNP%
			FROM RFC-1215	        --%DNP%
                    DisplayString
			FROM RFC1213-MIB
		    temporary
			FROM CISCO-SMI;
          
               chassis             OBJECT IDENTIFIER ::= { temporary 6 }

               -- Temporary Chassis Section


               -- (not the same as the IETF Chassis MIB)

          -- This group is present in all products.

               chassisType OBJECT-TYPE
                   SYNTAX  INTEGER {
			unknown(1)
			,multibus(2)
			,agsplus(3)
			,igs(4)
			,c2000(5)
			,c3000(6)
			,c4000(7)
			,c7000(8)
			,cs500(9)
			,c7010(10)
			,c2500(11)
			,c4500(12)
			,c2102(13)
			,c2202(14)
			,c2501(15)
			,c2502(16)
			,c2503(17)
			,c2504(18)
			,c2505(19)
			,c2506(20)
			,c2507(21)
			,c2508(22)
			,c2509(23)
			,c2510(24)
			,c2511(25)
			,c2512(26)
			,c2513(27)
			,c2514(28)
			,c2515(29)
			,c3101(30)
			,c3102(31)
			,c3103(32)
			,c3104(33)
			,c3202(34)
			,c3204(35)
			,accessProRC(36)
			,accessProEC(37)
			,c1000(38)
			,c1003(39)
			,c1004(40)
			,c2516(41)
			,c7507(42)
			,c7513(43)
			,c7506(44)
			,c7505(45)
			,c1005(46)
			,c4700(47)
			,c2517(48)
			,c2518(49)
			,c2519(50)
			,c2520(51)
			,c2521(52)
			,c2522(53)
			,c2523(54)
			,c2524(55)
			,c2525(56)
			,c4700S(57)
			,c7206(58)
			,c3640(59)
			,as5200(60)
			,c1601(61)
			,c1602(62)
			,c1603(63)
			,c1604(64)
			,c7204(65)
			,c3620(66)
			,wsx5301(67)			--%DNP% project cancelled, can reuse assignment
			,wsx3011(68)
			,mc3810(69)
			,c3830(70)			--%DNP% project cancelled, can reuse assignment
			,c3880(71)			--%DNP% project cancelled, can reuse assignment
			,c1503(72)
			,as5300(73)
			,as2509RJ(74)
			,as2511RJ(75)
			,c3800(76)			--%DNP% project cancelled, can reuse assignment 
			,c2501FRADFX(77)
			,c2501LANFRADFX(78)
			,c2502LANFRADFX(79)
			,wsx5302(80)		
			,c1605(81)
			,c12012(82)
-- %DNP% cisco4800 cancelled. reuse the assignment 83.
			,c12004(84)
			,c12008(85)
			,ubr7246(86)			-- Universal Broadband Router
			,c2610(87)			-- c2600 with 1 integrated ethernet interface 
			,c2612(88)			-- c2600 with an integrated ethernet and token ring interface
			,c2611(89)			-- c2600 with 2 integrated ethernet interfaces
			,ubr904(90)			-- Cisco Cable Modem (ubr - universal broadband router)
			,c6200(91)			-- Digital Subscriber Line Access Multiplexer(DSLAM) 
			,c3660(92)                      -- Six slot MARS Router
-- %DNP% c1700 cancelled, reuse the assignment 93.
			,c7202(94)                      -- Modular two slot router in the cisco7200 family
			,c2620(95)			-- c2600 platform with an onboard fast ethernet
			,c2621(96)			-- c2600 platform with two onboard fast ethernets
			,wsx9006(97)			-- cat9006 6 slot Milan. %DNP% until Jan 2000, contact cls.
			,wsx9009(98)			-- cat9009 9 slot Milan. %DNP% until Jan 2000, contact cls.
			,rpm(99)			-- Router Processor Module 
			,c1710(100)			-- VPN(Virtual Private Network) Security Router with 1 FastEthernet and 1 Ethernet interface onboard
			,c1720(101)                     
			,c7576(102)			-- Dual Independent RSP platform, 13 slots
			,c1401(103)			-- Router with 1 ethernet and 1 ATM25 interface 
			,c2613(104)			-- c2600 with 1 integrated token ring interface
			,ubr7223(105)			-- Universal Broadband Router
			,c6400Nrp(106)			-- c6400 Network Routing Processor
			,c801(107)			-- Cisco 800 platform with 1 ethernet and 1 BRI/ST 
			,c802(108)			-- Cisco 800 platform with 1 ethernet and 1 BRI U 
			,c803(109)			-- Cisco 800 platform with 1 ethernet 4-port hub, 1 BRI S/T, and 2 POTs 
			,c804(110)			-- Cisco 800 platform with 1 ethernet 4-port hub, 1 BRI U, and 2 POTs 
			,c7206VXR(111)			-- Cisco 7200 platform, VXR series chassis with 6 slots 
			,c7204VXR(112)			-- Cisco 7200 platform, VXR series chassis with 4 slots
			,c1750(113)			-- VoIP (Voice over IP) capable Cisco 1700 platform with 2 WIC/VIC slots and 1 VIC-only slot
			,mgx8850(114)			-- Cisco MGX8850 Multiservice Gigabit Switch with 32 half height slots
			,mgx8820(115)			-- Cisco MGX8820 Multiservice Gigabit Switch with 7 slots %DNP% until Nov 99, contact msosa
			,c805(116)			-- Cisco 800 platform with 1 ethernet and 1 serial WIC 
			,ws-c3508g-xl(117)		-- Cisco Catalyst 3508G-XL switch with 8 GBIC Gigabit ports, can run Standard or Enterprise edition software. 
			,ws-c3512-xl(118)		-- Cisco Catalyst 3512XL switch with 12 10/100BaseTX ports and 2 GBIC Gigabit ports, can run Standard or Enterprise edition software. 
			,ws-c3524-xl(119)		-- Cisco Catalyst 3524XL switch with 24 10/100BaseTX ports and 2 GBIC Gigabit ports, can run Standard or Enterprise edition software.
			,ws-c2908-xl(120)		-- Cisco Catalyst 2900XL series 8 port 10/100BaseTX switch
			,ws-c2916m-xl(121)		-- Cisco Catalyst 2916M-XL switch with 16 10/100BaseTX ports and 2 uplink slots.
			,ws-c2924-xl-v(122)		-- Cisco Catalyst 2924XL switch with 24 autosensing 10/100BaseTX ports; supports port-based VLANs; can run Standard or Enterprise edition software. 
			,ws-c2924c-xl-v(123)		-- Cisco Catalyst 2924C-XL switch with 22 autosensing 10/100BaseTX ports and 2 100BaseFX ports; supports port-based VLANs, can run Standard or Enterprise edition software.
			,ws-c2912-xl(124)		-- Cisco Catalyst 2912XL switch with 12 autosensing 10/100BaseTX ports, can run Standard or Enterprise edition software. 
			,ws-c2924m-xl(125)		-- Cisco Catalyst 2924M-XL switch with 24 autosensing 10/100BaseTX ports and 2 uplink slots, can run Standard or Enterprise edition software.
			,ws-c2912mf-xl(126)		-- Cisco Catalyst 2912MF-XL switch with 12 100BaseFX ports and 2 uplink slots; can only run Enterprise edition software.
			,c1407(127)			-- Cisco 1400 series router with 1 Ethernet and 1 ADSL interface, with 1407 chipset %DNP% until Aug 2000, contact kwee ADI chipset
			,c1417(128)			-- Cisco 1400 series router with 1 Ethernet and 1 ADSL interface, with 1417 chipset
			,cOpticalRegenerator(129)	-- Cisco Optical Regenerator
			,ws-c2924-xl(130)		-- Cisco Catalyst 2924XL with 24 10/100BaseTX switch ports; doesn't support port-based VLANs.
			,ws-c2924c-xl(131)		-- Cisco Catalyst 2924C-XL; doesn't support port-based VLANs.
			,ubr924(132)			-- Cisco UBR Cable Modem which is a UBR904 with 2 FXS Voice ports
                        ,ws-x6302-msm(133)              -- Catalyst 6000 or 6500 Series Multilayer Switch Module WS-X6302-MSM that directly interfaces to the switch's backplane to provide layer 3 switching.
			,cat5k-rsfc(134)		-- Router Switching Feature Card for the Catalyst 5000 that is treated as a standalone system by the NMS
                       ,cat6k-msfc(135)                -- Multilevel Switching Feature Card for Catalyst 6000 that is treated as a standalone system by the NMS %DNP% until Aug 99, contact mohsen
			,c7120-quadt1(136)		-- 7120 Series chassis with 2 10/100 FE interfaces, 4 T1/E1 interfaces
			,c7120-t3(137)			-- 7120 Series chassis with 2 10/100 FE interfaces, 1 T3 interface
			,c7120-e3(138)			-- 7120 Series chassis with 2 10/100 FE interfaces, 1 E3 interface
			,c7120-at3(139)			-- 7120 Series chassis with 2 10/100 FE interfaces, 1 T3 ATM interface
			,c7120-ae3(140)			-- 7120 Series chassis with 2 10/100 FE interfaces, 1 E3 ATM interface
			,c7120-smi3(141)		-- 7120 Series chassis with 2 10/100 FE interfaces, 1 OC3SMI ATM interface
			,c7140-dualt3(142)		-- 7140 Series chassis with 2 10/100 FE interfaces, 2 T3 interfaces
			,c7140-duale3(143)		-- 7140 Series chassis with 2 10/100 FE interfaces, 2 E3 interfaces
			,c7140-dualat3(144)		-- 7140 Series chassis with 2 10/100 FE interfaces, 2 T3 ATM interfaces 
			,c7140-dualae3(145)		-- 7140 Series chassis with 2 10/100 FE interfaces, 2 E3 ATM interfaces
			,c7140-dualmm3(146)		-- 7140 Series chassis with 2 10/100 FE interfaces, 2 OC3MM ATM interfaces
			,c827-quad-v(147)		-- Cisco 800 platform with 1 ethernet, 1 ADSL DMT issue 2, and 4 voice POTS FXS ports %DNP% until Jan 2000, contact fshu
			,ubr-7246-vxr(148)              -- Cisco 7246 Universal Broadband Router, VXR series %DNP% until Sep 99, contact ylu
			,c10400(149)			-- Cisco 10000 platform with 10 slots %DNP% until Mar 2000, contact bilafer
			,c12016(150)			-- Cisco 12000 platform with 16 slots
			,as5400(151)			-- Cisco AS5400 %DNP% until Dec 99, contact rmeadows Atlantis project developed in dial engineering for NUBU.
			,c7140-octt1(152)		-- 7140 Series chassis with 8 integrated T1/E1 serial ports
			,c7140-dualfe(153)		-- 7140 Series chassis with 2 integrated 10/100 FE interfaces
			,cat3548xl(154)			-- Catalyst 3548XL switch (WS-C3548-XL)
			,cat6006(155)			-- Catalyst 6000 with 6 slots 
			,cat6009(156)			-- Catalyst 6000 with 9 slots 
			,cat6506(157)			-- Catalyst 6000 Plus with 6 slots 
			,cat6509(158)			-- Catalyst 6000 Plus with 9 slots 
			,c827(159)			-- Cisco 800 platform with 1 ethernet, 1 ADSL DMT issue 2 %DNP% until Apr 2000, contact fshu
			,mc3810-v3(160)			-- Cisco MC3810-V3, capable of data, voice and video.  Supports 2 additional ports than the MC3810-V, used for optional access cards.
			,cat3524t-xl-en(161)		-- Cisco Catalyst 3524 switch (WS-C3524T-XL-EN) with 24 10/100 ports and 2 GBIC gigabit ports.  Runs Enterprise edition software and provides telephony power to attached IP telephones %DNP% until Mar 2000, contact pheller
			,c7507z(162)			-- Cisco 7507z chassis, Czbus capable, 7 slots
			,c7513z(163)			-- Cisco 7513z chassis, Czbus capable, 13 slots
			,c7507mx(164)			-- Cisco 7507mx chassis, Czbus capable, TDM (Time Division Multiplexing) backplane support, 7 slots
			,c7513mx(165)			-- Cisco 7513mx chassis, Czbus capable, TDM (Time Division Multiplexing) backplane support, 13 slots
			,ubr912-c(166)			-- Cisco uBR912-C Cable Modem with CSU/DSU WIC
			,ubr912-s(167)			-- Cisco uBR912-S Cable Modem with Serial WIC
			,ubr914(168)			-- Cisco uBR914 Cable Modem with removable WIC
			,c802-j(169)			-- Cisco 800 platform with 1 ethernet, 1 BRI S/T, and 1 Japanese BRI U %DNP% until Feb 2000, contact fshu
			,c804-j(170)			-- Cisco 800 platform with 1 ethernet, 2 POTS, 1 BRI/ST, and 1 Japanese BRI U %DNP% until Feb 2000, contact fshu
			,c6160(171)			-- Cisco 6160 DSLAM chassis %DNP% until May 2000, contact maniscar
			,c6015(172)			-- Cisco 6015 DSLAM chassis %DNP% until May 2000, contact pej
			,cat4232-l3(173)	-- Cisco Catalyst 4232-L3 layer 3 line card that is treated as a standalone system by the NMS
			,cOpticalRegeneratorDCPower(174)	-- Cisco Optical Regenerator with DC power supply
			,cat6k-msfc2(175)                -- Multilevel Switching Feature Card Version 2 for Catalyst 6000 that is treated as a standalone system by the NMS %DNP% until Apr 2000, contact mohsen
			,c7750-mrp200(176)			-- Cisco ICS 7750 Multiservice Route Processor 200 %DNP% until May 2000, contact kconry
			,c7750-ssp80(177)			-- Cisco ICS 7750 System Switch Processor 80 %DNP% until May 2000, contact kconry
			,mgx8230(178)			--  Multi Service Switch with 16 half-height slots %DNP% until Jun 2000, contact subrah
			,mgx8250(179)			--  Multi Service Switch with 32 half-height slots %DNP% until Jun 2000, contact subrah
			,cva122(180)			--   Cisco CVA122 Cable Voice Adapter (Residential Cable Modem with two Voice Ports)
			,cva124(181)			--   Cisco CVA124 Cable Voice Adapter (Residential Cable Modem with four Voice Ports)
			,as5850(182)			--  High End Dial Access Server %DNP% until sept 2000 contact samip
-- %DNP% reuse this assignmet	,ubr7100(183) A lower end version of the UBR7223, designed for hotels, MDUs and smaller cable operators
			,cat6509sp(184)			-- 9-slot Constellation+ vertical slot chassis %DNP% until Jun 2000 contact skilaru
			,mgx8240(185)			-- High Density Circuit Emulation Service Gateway chassis with two shelf controller slots and fifteen Service Modulesfor Private Line Service
			,cat4840g-l3(186)	--  Catalyst 4840G-L3 (WS-C4840G) Layer 3 Ethernet Switching System with Server Load Balancing  %DNP% until Apr 2000 contact abehbin
			,as5350(187)		--  Cisco low end Access server platform %DNP% until Dec 2000, contact nag
			,c7700(188)		--  Cisco Integrated Communication System (ICS) 7700 %DNP% until Dec 2000, contact suri
			,c7750(189)		--  Cisco Integrated Communication System (ICS) 7750 %DNP% until Dec 2000, contact suri
			,mgx8950(190)		--  Cisco Multiservice Gigabit Switch(180Gb) Chassis with 32 half height slots %DNP% until Dec 2000, contact subrah
			,ubr925(191)		-- Cisco UBR925 Cable Modem/Router with VOIP and hardware accelerated IPSEC
			,ubr10012(192)		-- Cisco uBR10000 platform with 8 broadband slots and 4 WAN slots
			,cat4k-gateway(193)		-- Catalyst 4000 Access Gateway line card supporting voice and WAN (Wide Area Network) interfaces as well as conferencing and transcoding services for operation with the Cisco Call Manager %DNP% until Aug 2000, contact wfried
			,c12016-8r(194)		-- Teracore ready 8 rail chassis for Cisco 12000 platform
			,c2650(195)		-- c2650 platform with 1 integrated fast ethernet interface
			,c2651(196)		-- c2650 platform with 2 integrated fast ethernet interfaces
			,c826-quad-v(197)       -- Cisco 800 platform with 1 ethernet, 1 ADSL over ISDN and 4 voice POTS FXS ports %DNP% until Aug 2000, contact jharrow
			,c826(198)              -- Cisco 800 platform with 1 ethernet, 1 ADSL over ISDN %DNP% until Aug 2000, contact jharrow
			,ws-c295012(199)		-- Cisco Catalyst c2950 switch with 12 10/100BaseTX ports (WS-c2950-12) %DNP% until Jan 2001, contact cchang
			,ws-c295024(200)		-- Cisco Catalyst c2950 switch with 24 10/100 BaseTX ports (WS-c2950-24) %DNP% until Jan 2001, contact cchang
			,ws-c295024c(201)		-- Cisco Catalyst c2950 switch with 24 10/100 BaseTX ports and 2 100BASE-FX uplink ports (WS-c2950-24C) %DNP% until Jan 2001, contact cchang
			,c1751(202)		-- Digital voice capable Cisco 1700 platform with 2 WIC/VIC slots and 1 VIC-only slot 
			,c1730-iad-8fxs(203)	-- Cisco 1700 class IAD (Integrated Access Device) with 8 FXS (Foreign Exchange Station) ports and DSL (Digital Subscriber Line) WIC %DNP% until Jan 2001, contact kwee
			,c1730-iad-16fxs(204)	-- Cisco 1700 class IAD (Integrated Access Device) with 16 FXS (Foreign Exchange Station) ports and DSL (Digital Subscriber Line) WIC %DNP% until Jan 2001, contact kwee
			,c626(205)		-- Cisco 600 DSL CPE pltaform with ADSL, DMT issue 1, 25M ATM interface
			,c627(206)		-- Cisco 600 DSL CPE pltaform with ADSL, DMT issue 2, 25M ATM interface
			,c633(207)		-- Cisco 600 DSL CPE platform with SDSL, 2B1Q line coding, serial interface (V.35/X.21)
			,c673(208)		-- Cisco 600 DSL CPE platform with SDSL, 2B1Q line coding, ethernet interface
			,c675(209)		-- Cisco 600 DSL CPE platform with ADSL, CAP, ethernet interface, POTS connector
			,c675e(210)		-- Cisco 600 DSL CPE platform with ADSL, CAP, ethernet interface, universal power supply
			,c676(211)		-- Cisco 600 DSL CPE platform with ADSL, DMT issue 1, ethernet interface
			,c677(212)		-- Cisco 600 DSL CPE platform with ADSL, DMT issue 2, ethernet interface
			,c678(213)		-- Cisco 600 DSL CPE platform with ADSL, CAP/DMT/G.Lite, ethernet interface
			,c3661-ac(214)		-- 1 Fast Ethernet version of c3660 with a AC power supply
			,c3661-dc(215)		-- 1 Fast Ethernet version of c3660 with a DC power supply
			,c3662-ac(216)		-- 2 Fast Ethernet version of c3660 with a AC power supply
			,c3662-dc(217)		-- 2 Fast Ethernet version of c3660 with a DC power supply
			,c3662-ac-co(218)		-- 2 Fast Ethernet version of c3660 with a AC power supply for Telco's
			,c3662-dc-co(219)		-- 2 Fast Ethernet version of c3660 with a DC power supply for Telco's
			,ubr7111(220)			-- Low-end version of the Universal Broadband Router with 1 PA slot, 1 fixed RF line card (MC11C) and integrated upconvertor, designed for hotels, MDUs and smaller cable operators
			,ubr7111e(221)			-- Low-end version of the Universal Broadband Router with 1 PA slot, 1 fixed RF line card (MC11E) and integrated upconvertor, designed for hotels, MDUs and smaller cable operators %DNP% until Jun 2001, contact azlina-group
			,ubr7114(222)			-- Low-end version of the Universal Broadband Router with 1 PA slot, 1 fixed RF line card (MC14C) and integrated upconvertor, designed for hotels, MDUs and smaller cable operators
			,ubr7114e(223)			-- Low-end version of the Universal Broadband Router with 1 PA slot, 1 fixed RF line card (MC14E) and integrated upconvertor, designed for hotels, MDUs and smaller cable operators %DNP% until Jun 2001, contact azlina-group
			,c12010(224)			-- Cisco 12000 platform with 10 slots
			,c8110(225)			-- Cisco 8110 (ATM network termination device) with 3 Line Interface module slots
			,c8120(226)			-- Cisco 8120 (ATM network termination device) with 3 Line Interface module(LIM) slots, and 2 Wan Interface Card (WIC) slots %DNP% until Jul 2001, contact jnaumann
			,ubr905(227)			-- Cisco uBR905 Cable Modem with hardware accelerated IPSEC %DNP% until Oct 2000, contact jgao abudin
			,ids(228)			-- CS IDS is a network-based, real-time intrusion detection system.  The NetRanger system has a distributed architecture and consists of two physical components: the Director, a scalable remote management system, and the Sensor, a high-performance, "plug-and-play" appliance %DNP% until Jan 2001, contact mhossain
			,soho77(229)			-- Cisco SOHO (Small Office Home Office) ADSL Router, 1 Ethernet and 1 ADSL G.992.1 (G.DMT) and G.992.2 (G.Lite) Interface %DNP% until Nov 2000, contact jharrow
			,soho76(230)			-- Cisco SOHO (Small Office Home Office) ADSL over ISDN Router, 1 Ethernet and 1 ADSL ETSI/ITU-T G.992.1 Annex B (G.DMT) Interface %DNP% until Nov 2000, contact jharrow
			,c7150-dualfe(231)		-- 7150 Series chassis with 2 integrated 10/100 FE interfaces
			,c7150-octt1(232)		-- 7150 Series chassis with 8 integrated T1/E1 serial ports
			,c7150-dualt3(233)		-- 7150 Series chassis with 2 10/100 FE interfaces, 2 T3 interfaces
			,olympus(234)			-- Cisco VPN (Virtual Private Network) Router with 4 10/100/1000 Gigabit ethernet integrated interfaces %DNP% until may 2001, contact ahase
			,ws-c2950t-24(235)		-- Cisco Catalyst c2950 switch with 24 10/100BaseT ports and 2 10/100/1000BaseT ports %DNP% until Jan 2001, contact cchang
			,cvps1110(236)			-- Cisco VLAN Policy Server 1110 manages VLAN-based policies to control user access to a LAN, leveraging existing authentication mechanisms such as Windows Domain Controllers and Novell's NDS. This policy server is part of CiscoWorks2000 User Registration Tool product.
			,ccontentengine(237)		-- Cisco Content Engine Chassis.  The Cisco Content Engine is a Content Networking product that accelerates content delivery, ensuring maximum scalability and availability of content.  The Content Engines offer caching, Content Delivery Network (CDN) services, employee internet management (e.g., URL filtering) and proxy services
			,ciad2420(238)			-- Integrated Access Device 2420 (IAD2420) chassis with Analog (8/16) FXS ports with T1 or ADSL (Asymmetrical Digital Subscriber Line) Uplinks
			,c677i(239)			-- Cisco 600 DSL CPE platform with ASDL, DMT issue 2 over ISDN, ethernet interface
			,c674(240)			-- Cisco 600 DSL CPE platform with G.SHDSL, ethernet interface
			,cdpa7630(241)			-- The Cisco Digital PBX Adapter (DPA) enables the integration of Cisco Call Manager with Octel voice mail systems
			,cat355024(242)			-- Catalyst 3550 24 10/100 ports + 2 Gig uplinks fixed configuration Layer 2/Layer 3 Ethernet Switch %DNP% until May 2001, contact paulines
			,cat355048(243)			-- Catalyst 3550 48 10/100 ports + 2 Gig uplinks fixed configuration Layer 2/Layer 3 Ethernet Switch %DNP% until May 2001, contact paulines
			,cat355012t(244)		-- Catalyst 3550 12 1000T ports fixed configuration Layer 2/Layer 3 Ethernet Switch %DNP% until May 2001, contact paulines
			,cat2924-lre-xl(245)		-- Cisco Catalyst c2924XL switch (WS-C2924-LRE-XL) with 24 10BaseS VDSL ports and 4 10/100BaseTX ports %DNP% until Mar 2001, contact arnoldb
			,cat2912-lre-xl(246)		-- Cisco Catalyst c2912XL switch (WS-C2912-LRE-XL) with 12 10BaseS VDSL ports and 4 10/100BaseTX ports %DNP% until Mar 2001, contact arnoldb
			,cva122e(247)			-- Cisco CVA122-e Cable Voice Adapter(Residential Cable Modem with two voice ports)- European version 
			,cva124e(248)			-- Cisco CVA124-e Cable Voice Adapter(Residential Cable Modem with four voice ports)- European version
			,curm(249)			-- Universal Router Module for the IGX platform
			,curm2fe(250)			-- Universal router module with 2 Fast Ethernet interfaces for IGX platform
			,curm2fe2v(251)			-- Universal Router Module, with 2 Fast Ethernet ports, and 2 digital voice ports (T1 or E1)
			,c7401VXR(252)			-- Cisco 7400 Family, 1 Slot router %DNP% until Feb 2001, contact taz
			,c951(253)			-- VOFDM and DOCSIS based wireless access router with 1 ethernet interface, and 1 wireless interface %DNP% until May 2001, contact afiguere
			,c952(254)			-- VOFDM and DOCSIS based wireless access router with 1 ethernet interface, 1 wireless interface, and 2 POTS voice ports %DNP% until May 2001, contact afiguere
			,cap340(255)			-- Aironet Wireless LAN Access Point 340 series
			,cap350(256)			-- Cisco Wireless LAN Access Point 350 series %DNP% until Mar 2001, contact huizhaow
			,cdpa7610(257)			-- The Cisco Digital PBX Adapter (DPA) enables the integration of Cisco Call Manager with Octel voice mail systems
			,c828(258)			-- Cisco 800 platform with 1 Ethernet, 1 G.991.2 (G.shdsl) Interface, data only model %DNP% until Apr 2001, contact pleung
			,soho78(259)			-- SOHO (Small Office Home Office) G.SHDSL Router, 1 Ethernet and 1 G.991.2 (G.shdsl) Interface, data only model %DNP% until Apr 2001, contact pleung
			,c806(260)			-- Cisco SOHO (Small Office Home Office) router with 4 hubbed 10BaseT Ethernet LAN interfaces and 1 10BaseT Ethernet WAN interface %DNP% until Jun 2001, contact jharrow 
			,c12416(261)			-- Cisco 12000 platform with 16 slots and 10G Fabric card
			,ws-c2948g-l3-dc(262)		-- A fixed-configuration Layer 3 Ethernet switch featuring IP, IPX, and IP mulitcast with 48 10/100BaseTX ports and 2 GBIC Gigabit ports using DC power
			,ws-c4908g-l3-dc(263)		-- A fixed-configuration L3 Ethernet switch featuring IP,IPX and IP multicast with 8 GBIC ports using DC power
			,c12406(264)			-- Cisco 12400 platform with 6 slots
			,pix-firewall506(265)		-- Cisco PIX Firewall 506
			,pix-firewall515(266)		-- Cisco PIX Firewall 515
			,pix-firewall520(267)		-- Cisco PIX Firewall 520
			,pix-firewall525(268)		-- Cisco PIX Firewall 525
			,pix-firewall535(269)		-- Cisco PIX Firewall 535
			,c12410(270)			-- Cisco 12410 platform with 10 slots
			,c811(271)			-- ISDN router for Japan with 1 10BaseT Ethernet port, 1 ISDN BRI(Basic Rate Interface) U, integrated DSU(Data Service Unit)
			,c813(272)			-- ISDN router for Japan with 10 BaseT 4 ports hub , 1 ISDN BRI(Basic Rate Interface) U, integrated DSU(Data Service Unit) and 2 RJ-11
			,c10720(273)			-- IP + Optical Access Router
            ,cMWR1900(274)			-- The Mobile Wireless router is a router targeted at application in a cell site Base Transciever Station (BTS) providing T1/E1 backhaul connections to the aggregation node in Radio Access Networks (RAN) %DNP% until Jan 2002, contact dblanken
			,c4224(275)			-- A standalone 24 port powered Ethernet switch, router and voice gateway
			,cWSC6513(276)			-- Catalyst 6000 series chassis with 13 slots 
			,c7603(277)			-- Cisco Internet Router 7600 Series Chassis with 3 slots 
			,c7606(278)			-- Cisco Internet Router 7600 Series Chassis with 6 slots 
			,c7401ASR(279)			-- Cisco 7400 platform, ASR series with 1 slot %DNP% until Mar 2001, contact mhyne taz
			,cVG248(280)			-- Cisco VoIP Voice Gateway for connecting analog telephones fax machines to a Cisco Call Manager based system %DNP% until Aug 2001, contact mloney
			,c1105(281)			-- CiscoWorks network management chassis
			,cSN5420(282)			-- SRBU Storage Router 1 Fiber Channel port, 1 Gigabit Ethernet port %DNP% until Mar 2001, contact bfine
			,cIcs7750Ce300(283)		-- Cisco ICS 7750 Content Engine %DNP% until Apr 2001, contact lrivas
			,cCe507(284)			-- Cisco Content Engine Model 507
			,cCe560(285)			-- Cisco Content Engine Model 560
			,cCe590(286)			-- Cisco Content Engine Model 590
			,cCe7320(287)			-- Cisco Content Engine Model 7320
			,c2691(288)			-- One Network Module slot, three WIC slot, two Fast Ethernet port MARS router 
			,c3725(289)			-- Two Network Module slot, three WIC slot, two Fast Ethernet port MARS router 
			,c3640A(290)			-- Cisco 3640 4-slot Modular Router %DNP% until Nov 2001, contact rmanian
			,c1760(291)			-- Analog/digital voice capable, 19" rack-mount (1RU) Cisco 1700 platform with 2 WIC/VIC slots and 2 VIC-only slots %DNP% until Nov 2001, contact kakozer
			,pix-firewall501(292)		-- Cisco PIX Firewall 501
			,c2610M(293)			-- c2600M chassis  with 1 integrated ethernet interface
			,c2611M(294)			-- c2600M chassis with 2 integrated ethernet interfaces
			,cGP10(295)			-- Cisco GSM Port %DNP% until Sep 2001, contact rdatla
			,cMC21(296)			-- Cisco GSM Mobility Controller %DNP% until Sep 2001, contact rdatla
			,cSN51(297)			-- Cisco GPRS Service Node %DNP% until Sep 2001, contact rdatla
			,c12404(298)			-- Cisco 12400 platform with 4 slots
			,c9004(299)			-- Cisco 9000 Chassis
			,c3631-co(300)			-- Two Network Module Slot, two WIC slot, one Fast Ethernet port MARS router %DNP% until Aug 2001, contact jechen
			-- reuse this assignment    c3631-dc-co(301)    %DNP% contact jechen
			,cat295012g(302)		-- Cisco Catalyst c2950 switch with 12 10/100 BaseTX ports and 2 GBIC (Gigabit Interface Converter) slots (WS-c2950g-12) %DNP% until Dec 2001, contact hliao
			,cat295024g(303)		-- Cisco Catalyst c2950 switch with 24 10/100 BaseTX ports and 2 GBIC (Gigabit Interface Converter) slots (WS-c2950g-12) %DNP% until Dec 2001, contact hliao
			,cat295048g(304)		-- Cisco Catalyst c2950 switch with 48 10/100 BaseTX ports and 2 GBIC (Gigabit Interface Converter) slots (WS-c2950g-12) %DNP% until Dec 2001, contact hliao
			,cat295024s(305)		-- Cisco Catalyst c2950 switch with 24 10/100 BaseSX ports (Single Mode) and 2 GBIC (Gigabit Interface Converter) slots (WS-c2950g-12) %DNP% until Dec 2001, contact hliao
			,cat355012g(306)		-- 10 Gig (GBIC) + 2 10/100/1000baseT ports, fixed configuration layer 2/3 Ethernet switch %DNP% until Nov 2001, contact madison
			,cCe507av(307)			-- Cisco Content Engine Model 507-AV
			,cCe560av(308)			-- Cisco Content Engine Model 560-AV
			,cIe2105(309)			-- The Cisco Intelligence Engine 2100 series is a new form of network device that provides intelligent network interface to applications and users
			,c3745(310)			-- 3700 family four slot modular router %DNP% until Dec 2001, contact rmanian
			,c10005(311)			-- Cisco 10000 platform with 7 slots %DNP% until Feb 2002, contact enjimene
			,c10008(312)			-- Cisco 10000 platform with 7 slots %DNP% until Feb 2002, contact enjimene
			,c7304(313)			-- Cisco 7300 Chassis
			,rpm-xf(314)			-- Chassis for RPM-XF router module %DNP% until Feb 2002, contact subrah
			,osm-4oc3-pos-sm-ir(315)	-- Optical Service Module, 4 port OC3 pos, Singlemode, Intermediate Range with 4 Gigabit Ethernet ports %DNP% until Nov 2001, contact vkamma
			,osm-4oc3-pos-mm-sr(316)	-- Optical Service Module, 4 port OC3 POS, Multimode, Short Range with 4 Gigabit Ethernet ports %DNP% until Nov 2001, contact vkamma
			,osm-4oc3-pos-sm-lr(317)	-- Optical Service Module, 4 port OC3 POS, Singlemode, Long Range with 4 Gigabit Ethernet ports %DNP% until Nov 2001, contact vkamma
			,c1721(318)			-- Enhanced 1720 with support for onboard Fast Ethernet and 2 WAN Interface cards and optional hardware encryption module %DNP% until Feb 2002, contact rameshs
			,cat4000-sup3(319)		-- Catalyst 4000 Supervisor III %DNP% until Mar 2002, contact sdobrota
			,c827h(320)			-- Cisco 800 platform with 4-port 10Base-T Ethernet, and 1 ADSL over POTS Interface, data only model %DNP% until Oct 2001, contact rhsu2k
			,soho77h(321)			-- SOHO (Small Office Home Office) Router, 4-port 10Base-T Ethernet, and 1 ADSL over POTS Interface, data only model  %DNP% until Oct 2001, contact rhsu2k
			,cWSC6503(322)			-- Catalyst 6000 series chassis with 3 slots 
			,pix-firewall506e(323)		-- Cisco PIX Firewall 506E %DNP% until Dec 2001, contact tmok, dcalia
			,pix-firewall515e(324)		-- Cisco PIX Firewall 515E %DNP% until Dec 2001, contact tmok, dcalia
			,cat355024-dc(325)		-- Catalyst 3550 10/100Base-Tx ports + 2 Gig uplinks fixed configuration Layer 2/Layer 3 Ethernet Switch with DC power %DNP% until Feb 2002, contact jijiang
			,ccontentengine2636(326)	-- Cisco Content Engine Module for 26xx and 36xx series platforms
			,ccontentengine-dw2636(327)	-- Double Wide Cisco Content Engine Module for 26xx and 36xx series
			,c7750-mrp300(328)		-- Cisco ICS 7750 Multiservice Route Processor 300 %DNP% until Dec 2001, contact sundarbs
			,mgx-14-8830(329)		-- Cisco Multiservice Gigabit Switch with 14 half height slots %DNP% until Jan 2002, contact vvaidhya
			,wlse(330)			-- Wireless LAN Solution Engine %DNP% until Feb 2002 contact anewman
			,soho71(331)                    -- Cisco SOHO Platform(Small Office Home Office) router having 10BaseT 4 ports hubed Ethernet LAN interface and 1 10BaseT Ethernet WAN Interface %DNP% until FEB 2002, contact pleung
			,c6400-uac(332)                 -- Cisco 6400 Universal Access Concentrator
			,cat355024-mmf(333)			-- Catalyst 3550 24 10/100Mbps Multi Mode Fiber ports + 2 Gig uplinks fixed configuration Layer 2/Layer 3 Ethernet Switch %DNP% until May 2002, contact jijiang
			,airap-1200(341)		-- 1200 series WLAN Access Point with 1 10/100TX port, 1 CardBus slot, 1 Mini PCI slot %DNP% until May 2002, contact cjstack
			,cSN5428(342)			-- Storage Networking 5428 storage router with 2 SFP (Small Form  Factor Pluggable) GBIC Gigabit Ethernet ports and 8 SFP GBIC Fibre Channel ports %DNP% until May 2002, contact bobert
			,c2610XM(334)                   -- Cisco 2610XM platform with 1 integrated fast ethernet interfaces with SDRAM
			,c2611XM(335)                   -- Cisco 2611XM platform with 2 integrated fast ethernet interfaces with SDRAM
			,c2620XM(336)                   -- Cisco 2620XM platform with 1 integrated fast ethernet interfaces with SDRAM
			,c2621XM(337)                   -- Cisco 2621XM platform with 2 integrated fast ethernet interfaces with SDRAM
			,c2650XM(338)                   -- Cisco 2650XM platform with 1 integrated fast ethernet interfaces with SDRAM
			,c2651XM(339)                   -- Cisco 2651XM platform with 2 integrated fast ethernet interfaces with SDRAM
			,cat295024g-dc(340)		-- Cisco Catalyst c2950 switch with 24 10/100 BaseTX ports and 2 GBIC (Gigabit Interface Converter) slots and DC power(WS-c2950G-24-DC) %DNP% until Apr 2002, contact hliao
			,c7301(343)			-- Cisco 7300 platform, 1 Rack Unit (RU) application specific router with 1 slot %DNP% until Jan 2003, contact dhom
			,c12816(344)			-- Cisco 12816 platform with 16 slots %DNP% unitl Dec 2002, contact honyang, fyuan
			,c12810(345)			-- Cisco 12810 platform with 10 slots %DNP% unitl Dec 2002, contact honyang, fyuan
			,cat295024-lre-st(346)		-- Cisco Catalyst c2950 switch with 24 10BaseS VDSLPorts and 2 ST ( SFP or 10/100/1000 Base T) (WS-C2950ST-24-LRE) %DNP% until Nov 2002, contact kalyan
			,cat29508lre-st(347)		-- Cisco Catalyst c2950 switch with 8 10BaseS VDSL Ports and 2 ST (SFP or 10/100/1000 Base T) (WS-C2950ST-8-LRE) %DNP% until Nov 2002, contact kalyan
			,cat295024-lre-g(348)		-- Cisco Catalyst c2950 switch with 24 10BaseS VDSL Ports and 2 GBIC ( Gigabit Interface Converter ) slots (WS-C2950G-24-LRE) %DNP% until Nov 2002, contact kalyan
			,cat355024-pwr(349)		-- Catalyst 3550 10/100Base-Tx ports with inline power and 2 Gig uplinks fixed configuration Layer 2/Layer 3 Ethernet Switch %DNP% until Dec 2002, contact jaschen
			,cat295024sx(350)		-- Cisco Catalyst c2950 switch with 24 10/100 BaseTX ports and 2 fixed 1000Base Multimode fiber (SX) ports (WS-C2950SX-24)
			,cat2955-t12(351)		-- Cisco Catalyst c2950 Industrial switch with 12 10/100 and 2 10/100/1000 BaseT ports %DNP% until Feb 2003, contact teresang
			,cat2955-c12(352)		-- Cisco Catalyst c2950 Industrial switch with 12 10/100 BaseTX ports and 2 100 Base-FX ports %DNP% until Feb 2003, contact teresang
			,as5400-hpx(353) 		-- chassis for cisco As5400HPX
			,as5350-hpx(354)                -- chassis for cisco AS5350HPX %DNP% until Jun 2002, contact vdukki
			,c3250(355)			-- cisco 3250 Mobile Router %DNP% until May 2002, contact srikkris
			,c837(356)			-- Cisco 837 platform with 4-port 10/100 Base-T Ethernet Switch, 1 ADSL over POTS interface, data only model, hardware encryption %DNP% until Dec 2002, contact vimala
			,soho97(357)			-- SOHO (Small Office Home Office) Router, with 4-port 10/100 Base-T Ethernet Switch, 1 ADSL over POTS interface, data only model %DNP% until Dec 2002, contact vimala
			,c831(358)			-- Cisco 831 platform with 4-port 10/100 Base-T Ethernet Switch, 1 10Base-T Ethernet WAN interface, hardware encryption %DNP% until Dec 2002, contact vimala
			,soho91(359)			-- SOHO (Small Office Home Office) Router, with 4-port 10/100 Base-T Ethernet Switch, 1 10Base-T Ethernet WAN interface %DNP% until Dec 2002, contact vimala
			,c836(360)			-- Cisco 836 platform with 4-port 10/100 Base-T Ethernet Switch, 1 ADSL over ISDN interface, 1 ISDN BRI S/T interface, hardware encryption %DNP% until Dec 2002, contact vimala
			,soho96(361)			-- SOHO (Small Office Home Office) Router, with 4-port 10/100 Base-T Ethernet Switch, 1 ADSL over ISDN interface, 1 ISDN BRI S/T interface %DNP% until Dec 2002, contact vimala
			,airap-1100(362)		-- 1100 series WLAN Access Point with 1 10/100TX port, 1 IEEE 802.11 radio port %DNP% until Oct 2002, contact fpang
			,ciad2430(363)			-- Integrated Access Device 2430 (IAD2430) chassis with Analog (8/16/24) FXS ports with T1/E1 ports, 1 Fast Ethernet port, 1 WIC Slot %DNP% until Apr 2002, contact ypatel
			,cat2955-s12(364)		-- Cisco Catalyst c2955 Industrial switch with 12 10/100 Base T ports and 2 100 Base-LX Single Mode Uplink ports %DNP% until Feb 2003, contact teresang
			,c7609(365)			-- 9 slots chassis in Cisco 7600 family
			,cWSC65509(366)			-- 9 slots chassis in Catalyst 6500 family %DNP% until Dec 2004, contact fxu, tjw, lijiang
			,cat375024(367)			-- Catalyst 3750 24 10/100 ports + 2 Gigabit SFP ports fixed configuration Layer 2/Layer 3 Ethernet Stackable Switch. (SFP Small Formfactor Pluggable) %DNP% until Feb 2003, contact murali
			,cat375048(368)			-- Catalyst 3750 48 10/100 ports + 4 Gigabit SFP ports fixed configuration Layer 2/Layer 3 Ethernet Stackable Switch. (SFP Small Formfactor Pluggable) %DNP% until Feb 2003, contact murali
			,cat375024TS(369)		-- Catalyst 3750 24 10/100/1000 ports + 4 Gigabit SFP ports fixed configuration Layer 2/Layer 3 Ethernet Stackable Switch. (SFP Small Formfactor Pluggable) %DNP% until Feb 2003, contact murali
			,cat375024T(370)		-- Catalyst 3750 24 10/100/1000 ports fixed configuration Layer 2/Layer 3 Ethernet Stackable Switch. %DNP% until Feb 2003, contact murali
			,cMWR1941DC(371)		-- The Mobile Wireless Router (MWR-1941-DC) is a router with a universal power supply targeted at application in a cell site Base Transceiver Station (BTS) providing T1/E1 backhaul connections to the aggregation node in Radio Access Networks (RAN) %DNP% until Dec 2002, contact dblanken
			,cVG200(372)			-- The Cisco VG200 chassis for Voice-over-IP (VoIP) Gateway
			,airap1210(373)			-- 1200 series WLAN Access Point on Cisco IOS platform with 1 10/100TX port, 1 CardBus slot, 1 Mini PCI slot
			,cat375048PS(374)		-- Catalyst 3750 48 10/100 ports with In-Line Power + 2 Gigabit SFP ports fixed configuration Layer 2/Layer 3 Ethernet Stackable Switch.(SFP Small Formfactor Pluggable) %DNP% until July 2003, contact rneal
			,cat375024PS(375)		-- Catalyst 3750 24 10/100 ports with In-Line Power + 2 Gigabit SFP ports fixed configuration Layer 2/Layer 3 Ethernet Stackable Switch(SFP Small Formfactor Pluggable) %DNP% until July 2003, contact rneal
			,cat297024(376)			-- Catalyst 2970 24: 24 10/100/1000 ports fixed configuration Layer 2 Ethernet Switch %DNP% until May 2003, contact pritesh
			,c7613(377)			-- Cisco Internet router 7600 Series Chassis with 13 slots 
			,cSn54282(378)			-- Storage Networking 5428-2 storage router with 2 SFP (Small Form Factor Pluggable) GBIC Gigabit Ethernet ports and 8 SFP GBIC Fibre Channel ports. %DNP% until Feb 2002, contact crjohnso
			,cat3750-12ge-sfp(379)		-- Catalyst 3750 12 Ethernet Gigabit SFP ports stackable switch. (SFP: Small Form factor Pluggable) %DNP% until Jun 2003, contact glovblom
			,airbr-1410(380)		-- 1410 Series Wireless LAN Bridge on Cisco IOS platform with 1 10/100Tx port and 1 5-GHz radio
			,cWSC6509neba(381)		-- Catalyst 6500 series chassis with 9 slots %DNP% until May 2003, contact lpbinh tjw fxu
			,c1711(382)			-- Enhanced security router with 4 FastEthernet switch ports, 1 Analog modem port, 1 FastEthernet port and a hardware encryption module %DNP% until Jul 2003, contact mananthr
			,c1712(383)			-- Enhanced security router with 4 FastEthernet switch ports, 1 Basic Rate Interface(S/T)  data port, 1 FastEthernet port and a hardware encryption module. %DNP% until Jul 2003, contact mananthr
			,c1701(384)			-- c1701 is a re-packaging of existing products to create a fixed configuration sku. It has ADSLoPOTs WIC and ISDN BRI (S/T) WIC riveted into it.
			,cat29408TT(385)		-- Catalyst 2940 L2 switch with 8 10/100 copper ports and 1 10/100/1000 copper uplink port.
			,cat29408TF(386)		-- Catalyst 2940 L2 switch with 8 10/100 copper ports, 1 100 FX Uplink port and 1 Gigabit SFP Module slot.
			,c3725xm(387)			-- Two Network Module Slots, Four WIC slots, Two Gigabit Ethernet ports MARS router %DNP% until Dec 2003, contact abhalgat
			,c3745xm(388)			-- Four Network Module Slots, Four WIC slots, Two Gigabit Ethernet ports 3700 family router %DNP% until Dec 2003, contact abhalgat
			,c2430iad-24fxs(389)		-- cIAD2430 with 24FXS, 2FE %DNP% until Dec 2003, contact ypatel
			,c2431iad-8fxs(390)		-- cIAD2431 with 8FXS, 2FE, 1T1/E1, 1 vwic slot %DNP% until Dec 2003, contact ypatel
			,c2431iad-16fxs(391)		-- cIAD2431 with 16FXS, 2FE, 1T1/E1, 1 vwic slot %DNP% until Dec 2003, contact ypatel
			,c2431iad-1t1e1(392)		-- cIAD2431 with 2FE, 2T1/E1, 1 vwic slot %DNP% until Dec 2003, contact ypatel
			,c2432iad-24fxs(393)		-- cIAD2432 with 24FXS, 2FE, 2T1E1, 1 vwic slot %DNP% until Dec 2003, contact ypatel
			,airap350ios(394)		-- Cisco Wireless LAN Access Point 350 series on IOS platform with 1 10/100TX port, 1 IEEE 802.11 radio port
			,c3220(395)			-- Cisco 3220 Platform - Mobile Access Router Chassis. %DNP% until May 2003, contact pnoone
			,cat295024-lre-st-997(396)      -- Cisco Catalyst2905 Long Reach Ethernet switch that confirms to ETSI 997 with 24 LRE interfaces, 2 10/100/1000 Small form factor copper interfaces and DC power supply(WS-C2905ST-24-LRE-997)
			,cVG324(397)			-- Line side Analog Gateway with 24FXS Analog ports %DNP% until Dec 2003 , contact  ypatel
			,cat295048t(398)		-- Cisco Catalyst c2950 switch with 48 10/100BaseT ports and 2 10/100/1000 BaseT ports %DNP% until Oct 2003 , contact amian
			,cat295048sx(399)		-- Cisco Catalyst c2950 switch with 48 10/100BaseTX ports and 2 fixed 1000Base Multimode fiber (SX) ports %DNP% until Oct 2003 , contact amian
			,cat6k-sup720(400)		-- Catalyst 6500 Supervisor Module 720 CPU board that is treated as a standalone system by the NMS %DNP% until July 2003, contact lpbinh tjw fxu
			,cat297024-ts(401)		-- Catalyst 2970 24 10/100/1000 ports + 4 Gigabit SFP ports fixed configuration Layer 2 Ethernet Switch. %DNP% until Aug 2003, contact sudhi
 			,cat356048-ps(402)		-- Catalyst 3560 48 10/100 ports with In-Line Power + 4 Gigabit SFP ports fixed configuration Layer 2/Layer 3 Ethernet Switch.(SFP Small Formfactor Pluggable) %DNP% until Oct 2003, contact rneal
 			,cat356024-ps(403)			-- Catalyst 3560 24 10/100 ports with In-Line Power + 2 Gigabit SFP ports fixed configuration Layer 2/Layer 3 Ethernet Switch.(SFP Small Formfactor Pluggable) %DNP% until Oct 2003, contact rneal
 			,cat3750g-16td(420)		-- Cisco Catalyst 3750 switch with 16 gigabit and one 10G ethernet port (WS-C3750G-16TD)
			,cat3750G24-ps(426)		-- Catalyst 3750 24 10/100/1000 Power over Ethernet ports + 4 Gigabit Ethernet SFP ports Layer 2/Layer 3 Module.(SFP Small Form factor Plugable)  %DNP% until Oct 2004, contact pritesh
			,cat3750G48-ps(427)		-- Catalyst 3750 48 10/100/1000 Power over Ethernet ports + 4 Gigabit Ethernet SFP ports Layer 2/Layer 3 Module.(SFP Small Form factor Plugable)  %DNP% until Oct 2004, contact pritesh 
			,cat3750G48-ts(428)		-- Catalyst 3750 48 10/100/1000 ports + 4 Gigabit Ethernet SFP ports Layer 2/Layer 3 Module.(SFP Small Form factor Plugable)  %DNP% until Oct 2004, contact pritesh
			,cat297048-ts(429)		-- Catalyst 2970 48 10/100/1000 ports + 4 Gigabit SFP ports fixed configuration Layer 2 Ethernet Switch. %DNP% until Oct 2004, contact pritesh
 			,cat3560G24-ps(432)		-- Catalyst 3560 24 10/100/1000 Power over Ethernet ports + 4 Gigabit Ethernet SFP ports Layer 2/Layer 3 Switch.(SFP Small Form factor Pluggable)  %DNP% until Nov 2004, contact pritesh
                        ,cat3560G24-ts(433)		-- Catalyst 3560 24 10/100/1000 Ethernet ports + 4 Gigabit Ethernet SFP ports Layer 2/Layer 3 Switch.(SFP Small Form factor Pluggable)  %DNP% until Nov 2004, contact pritesh
			,cat3560G48-ps(434)		-- Catalyst 3560 48 10/100/1000 Power over Ethernet ports + 4 Gigabit Ethernet SFP ports Layer 2/Layer 3 Switch.(SFP Small Form factor Pluggable)  %DNP% until Nov 2004, contact pritesh 
			,cat3560G48-ts(435)		-- Catalyst 3560 48 10/100/1000 ports + 4 Gigabit Ethernet SFP ports Layer 2/Layer 3 Switch.(SFP Small Form factor Pluggable)  %DNP% until Nov 2004, contact pritesh
                        ,cat3750G24-ts1u(441)		-- Catalyst 3750 24 10/100/1000 Ethernet ports + 4 Gigabit Ethernet SFP ports Layer 2/Layer 3 Module.(SFP Small Form factor Plugable)  %DNP% until Oct 2004, contact pritesh
			,c371098-hp-001(443)            --  24 port Gigabit Ethernet switch module for HP ProLiant BL p-class server chassis %DNP% until Feb 2005, contact mitchell
		}

                   ACCESS  read-only
                   STATUS  deprecated
                   DESCRIPTION
                           "Chassis type."
                   ::= { chassis 1 }

               chassisVersion OBJECT-TYPE
                   SYNTAX  DisplayString
                   ACCESS  read-only
                   STATUS  deprecated
                   DESCRIPTION
                           "Chassis hardware revision level, or an empty
                           string if unavailable."
                   ::= { chassis 2 }

               chassisId OBJECT-TYPE
                   SYNTAX  DisplayString
                   ACCESS  read-write
                   STATUS  deprecated
                   DESCRIPTION
                           "Unique ID string. Defaults to chassis serial
                           number if available, otherwise empty. Can
                           also be set with 'snmp-server chassis-id'."
                   ::= { chassis 3 }

               romVersion OBJECT-TYPE
                   SYNTAX  DisplayString
                   ACCESS  read-only
                   STATUS  deprecated
                   DESCRIPTION
                           "ROM monitor version."
                   ::= { chassis 4 }

               romSysVersion OBJECT-TYPE
                   SYNTAX  DisplayString
                   ACCESS  read-only
                   STATUS  deprecated
                   DESCRIPTION
                           "ROM system software version, or an empty
                           string if unavailable."
                   ::= { chassis 5 }

               processorRam OBJECT-TYPE
                   SYNTAX  INTEGER
                   ACCESS  read-only
                   STATUS  deprecated
                   DESCRIPTION
                           "Bytes of RAM available to CPU."
                   ::= { chassis 6 }

               nvRAMSize OBJECT-TYPE
                   SYNTAX  INTEGER
                   ACCESS  read-only
                   STATUS  deprecated
                   DESCRIPTION
                           "Bytes of non-volatile configuration memory."
                   ::= { chassis 7 }

               nvRAMUsed OBJECT-TYPE
                   SYNTAX  INTEGER
                   ACCESS  read-only
                   STATUS  deprecated
                   DESCRIPTION
                           "Bytes of non-volatile configuration memory
                           in use."
                   ::= { chassis 8 }

               configRegister OBJECT-TYPE
                   SYNTAX  INTEGER
                   ACCESS  read-only
                   STATUS  deprecated
                   DESCRIPTION
                           "Value of configuration register."
                   ::= { chassis 9 }

               configRegNext OBJECT-TYPE
                   SYNTAX  INTEGER
                   ACCESS  read-only
                   STATUS  deprecated
                   DESCRIPTION
                           "Value of configuration register at next
                           reload."
                   ::= { chassis 10 }

               cardTable OBJECT-TYPE
                   SYNTAX  SEQUENCE OF CardTableEntry
                   ACCESS  not-accessible
                   STATUS  deprecated
                   DESCRIPTION
                            "Chassis card table."
                   ::= { chassis 11 }

               cardTableEntry OBJECT-TYPE
                   SYNTAX CardTableEntry
                   ACCESS  not-accessible
                   STATUS  deprecated
                   DESCRIPTION
                            "Chassis card table."
                   INDEX { cardIndex }
               ::= { cardTable 1 }

               CardTableEntry ::=
                   SEQUENCE {
                       cardIndex
                           INTEGER,
                       cardType
                           INTEGER,
                       cardDescr
                           DisplayString,
                       cardSerial
                           INTEGER,
                       cardHwVersion
                           DisplayString,
                       cardSwVersion
                           DisplayString,
                       cardSlotNumber
                           INTEGER,
                       cardContainedByIndex
                           INTEGER,
                       cardOperStatus
                           INTEGER,
                       cardSlots
                           INTEGER
                   }


          -- The following section describes the components of the
          -- table.

               cardIndex OBJECT-TYPE
                   SYNTAX  INTEGER
                   ACCESS  read-only
                   STATUS  deprecated
                   DESCRIPTION
                           "Index into cardTable (not physical chassis
                           slot number)."
                   ::= { cardTableEntry 1 }

--	1-19,25-39:	cpu-type cards			%DNP%
--	20-24,40-120:	csc cards			%DNP%
--	121-149:	more cpu-type cards		%DNP%
--	150-199:	c7xxx cards			%DNP%
--	200-229:	c4xxx nims			%DNP%
--	230-259:	c4700 & VIP port adapters	%DNP%
--	260-289:	MARs cards			%DNP%
--	290-309:	as5200 cards			%DNP%
--	310-329:	as5200 port adapters		%DNP%
--	330-359:	25xx cards			%DNP%
--	360-389:	16xx & 36xx cards		%DNP%
--	400-429:	more c4700 & VIP port adapters	%DNP%
--	430-459:	c38xx cards			%DNP%
--	460-479:	as5300 port adapters		%DNP%
--	480-499:	as5300 cards			%DNP%
--	500-529:	voice cards			%DNP%
--	530-559:	BFR cards			%DNP%
--	560-599:	more c4700 & VIP port adapters	%DNP%
--	600-629:	more MARS cards			%DNP%
--	630-649:	Nitro cards			%DNP%
--	650-699:	c6xxx cards			%DNP%
--	700-749:	Milan cards			%DNP%
--	750-799:	rpm cards			%DNP%
--	800-849:	more VIP port adapters		%DNP%
--	850-899:	Wide Area Switch common cards	%DNP%
--	900-949:	Catalyst 2900XL series cards	%DNP%
--	950-999:	Wide Area Switch Back Cards	%DNP% (also known as Line Modules)
--	1000-1049:	UBR cards			%DNP%
--	1050-1099:	more BFR cards			%DNP%
--	1100-1149:	more 16xx, 26xx, & 36xx cards	%DNP%
--	1150-1179:	7100 series cards		%DNP%
--	1180-1299:	yet more cpu-type cards		%DNP%
--	1300-1349:	10000 series cards		%DNP%
--	1350-1449:	AS5400 cards			%DNP%
--	1450-1500:	Common Cards			%DNP%
--	1501-1549:	Catalyst 6000 Cards		%DNP%
--	1550-1599:	Daughter Cards			%DNP%
--	1600-1649:	Dslam Cards			%DNP%
--	1650-1699:	ICS7000 series Cards	%DNP%
--	1700-1749:	CVA Cards	%DNP%
--	1750-1799:	Marvel (AS5850) Cards	%DNP%
--	1800-1849:	AS5350 Cards			%DNP%
--	1850-1899:	Catalyst 4000 Cards		%DNP% 
--	1900-1949:	more BFR Cards			%DNP%
--	1950-1999:	24xx Cards			%DNP%
--	2000-2049:	more c38xx cards		%DNP%
--	2050-2099:	10000Bases cards		%DNP%
--	2100-2150:      more c7xxx cards                %DNP%
--	2151-2199:	C7160 cards 			%DNP%
--	2200-2249:	yet more BFR cards		%DNP%
--	2250-2299:	more Wide Area Switch Back Cards/Line Modules	%DNP%
--	3000-3049:	more yet more BFR cards         %DNP%
--	3050-3099	more Wide Area Switch common cards (MGX, IGX series boxes)   %DNP%
--	4000-4049:	yet more 16xx, 26xx, & 36xx cards	%DNP%
--      4151-4200:	c32xx Cards		%DNP%
--

-- The expansions for some acronyms used for cardType enumerations are:
--	CSU : Channel Service Unit
--	DSU : Dial Service Unit
--	FT1 : Fractional T1
--	WIC : Wan Interface Card
--	DTR : Dedicated Token Ring
--	PM  : Port Module
--	PA  : Port Adapter

               cardType OBJECT-TYPE
                   SYNTAX  INTEGER {
--	1-19,25-39:	cpu-type cards			%DNP%
			unknown(1)
			,csc1(2)
			,csc2(3)
			,csc3(4)
			,csc4(5)
			,rp(6)
			,cpu-igs(7)
			,cpu-2500(8)
			,cpu-3000(9)
			,cpu-3100(10)
			,cpu-accessPro(11)
			,cpu-4000(12)
			,cpu-4000m(13)
			,cpu-4500(14)
			,rsp1(15)
			,rsp2(16)
			,cpu-4500m(17)
			,cpu-1003(18)
			,cpu-4700(19)
			,csc-m(20)
			,csc-mt(21)
			,csc-mc(22)
			,csc-mcplus(23)
			,csc-envm(24)
			,chassisInterface(25)
			,cpu-4700S(26)
			,cpu-7200-npe100(27)
			,rsp7000(28)
			,chassisInterface7000(29)
			,rsp4(30)
			,cpu-3600(31)
			,cpu-as5200(32)
			,c7200-io1fe(33)
			,cpu-4700m(34)
			,cpu-1600(35)
			,c7200-io(36)
			,cpu-1503(37)
			,cpu-1502(38)
			,cpu-as5300(39)
--	20-24,40-120:	csc cards			%DNP%
			,csc-16(40)
			,csc-p(41)
			,csc-a(50)
			,csc-e1(51)
			,csc-e2(52)
			,csc-y(53)
			,csc-s(54)
			,csc-t(55)
			,csc-r(80)
			,csc-r16(81)
			,csc-r16m(82)
			,csc-1r(83)
			,csc-2r(84)
			,sci4s(56)
			,sci2s2t(57)
			,sci4t(58)
			,mci1t(59)
			,mci2t(60)
			,mci1s(61)
			,mci1s1t(62)
			,mci2s(63)
			,mci1e(64)
			,mci1e1t(65)
			,mci1e2t(66)
			,mci1e1s(67)
			,mci1e1s1t(68)
			,mci1e2s(69)
			,mci2e(70)
			,mci2e1t(71)
			,mci2e2t(72)
			,mci2e1s(73)
			,mci2e1s1t(74)
			,mci2e2s(75)
			,csc-cctl1(100)
			,csc-cctl2(101)
			,csc-mec2(110)
			,csc-mec4(111)
			,csc-mec6(112)
			,csc-fci(113)
			,csc-fcit(114)
			,csc-hsci(115)
			,csc-ctr(116)
--	121-149:	more cpu-type cards		%DNP%
			,cpu-7200-npe150(121)
			,cpu-7200-npe200(122)
			,cpu-wsx5302(123)
			,gsr-rp(124)
-- %DNP% cisco4800 cancelled. reuse the assignment 125
			,cpu-3810(126)
			,cpu-2600(127)
			,cpu-rpm(128)
			,cpu-ubr904(129)		-- CPU card for Cisco Cable Modem (ubr - universal broadband router)
			,cpu-6200-mpc(130)		-- Maintenance processor card for c6200
			,cpu-1700(131)			-- CPU for Cisco 1700 series
			,cpu-7200-npe300(132)		-- Network processing engine (CPU card) for 7200 series 
			,cpu-1400(133)			-- CPU for Cisco 1400 series 
			,cpu-800(134)			-- CPU for Cisco 800 series products 
			,cpu-psm-1gbps(135)		-- Processor Switch Module 1 with 1.2Gbps switching capacity for MGX 8800 series chassis
			,cpu-psm-45gbps(136)		-- Processor Switch Module 2 with 45Gbps switching capacity for MGX 8800 series chassis %DNP% until Nov 99, contact msosa
			,cpu-7200-npe175(137)		-- Network processing engine (CPU card) for 7200 series
			,cpu-7200-npe225(138)		-- Network processing engine (CPU card) for 7200 series
			,cpu-1407(139)			-- CPU for Cisco 1407 only %DNP% until Aug 2000, contact kwee ADI chipset
			,cpu-1417(140)			-- CPU for Cisco 1417 only
			,cpu-psm1-1oc12(141)		-- Cisco MGX8800 Processor Switch Module 1 with 1 622Mbps port
			,cpu-optical-regenerator(142)	-- CPU for the Cisco Optical Regenerator chassis
			,cpu-ubr924(143)		-- CPU for the UBR924 Cisco Cable Modem
			,cpu-7120(144)			-- CPU for the Cisco 7120 series
			,cpu-7140(145)			-- CPU for the Cisco 7140 series
			,cpu-psm1-2t3e3(146)		-- Cisco MGX8800 Processor Switch Module 1 with 2 T3/E3 ports
			,cpu-psm1-4oc3(147)		-- Cisco MGX8800 Processor Switch Module 1 with 4 155Mbps ports
			,cpu-ses-psm1-4oc3(148)		-- Cisco SES Processor Switch Module 1 with 4 155Mbps ports %DNP% until Nov 99, contact sshegde
			,cpu-ubr91x(149)		-- CPU card for the UBR91X family of Cable Modems (912-c, 912-s, 914)
--	150-199:	c7xxx cards			%DNP%
			,sp(150)
			,eip(151)
			,fip(152)
			,hip(153)
			,sip(154)
			,trip(155)
			,fsip(156)
			,aip(157)
			,mip(158)
			,ssp(159)
			,cip(160)
			,srs-fip(161)
			,srs-trip(162)
			,feip(163)
			,vip(164)
			,vip2(165)
			,ssip(166)
			,smip(167)
			,posip(168)
			,feip-tx(169)
			,feip-fx(170)
			,cbrt1(178)
			,cbr120e1(179)
			,cbr75e(180)
			,vip2-50(181)
			,feip2(182)
			,acip(183)
			,mc11(184)			-- cable card 1 downstream 1 upstream
			,mc12a(185)			-- cable card 1 downstream 2 upstream 
			,io1fe-tx-isl(186)		-- Fast Ethernet I/O Controller which provides RJ45 and MII Connectors
			,geip(187)			-- Gigabit Ethernet Interface Processor 
			,vip4(188)			-- 4th Generation Versatile Interface Processor for the c7500 router 
			,mc14a(189)			-- cable card 1 downstream 4 upstream 
			,mc16a(190)			-- cable card 1 downstream 6 upstream 
			,mc11a(191)			-- modem card 1 downstream 1 upstream (ASIC)  
			,cip2(192)			-- channel interface processor 2 for the 7500 router family.  supports IBM ESCON and IBM Parallel (Bus & Tag) interface types.
			,mc16-eur(193)			-- cable card 1 downstream 6 upstream for Europe %DNP% until Oct 99, contact ylu
			,mc28(194)			-- cable card 2 downstream 8 upstream
			,vip4-80(195)		-- 4th Generation Versatile Interface Processor for the c7500 router
			,vip4-50(196)		-- 4th Generation Versatile Interface Processor for the c7500 router, lower performance than vip4-80 card
			,io-e-ge(197)		-- C7200 I/O Controller with GE(1000Mbps) + E(10Mbps) interface
			,io-2fe(198)		-- C7200 I/O Controller with 2FE (10/100Mbps) interface
			,geip-plus(199)		-- Enhanced Gigabit Ethernet Interface Processor for the c7500 router %DNP% until Jul 2000, contact shhwang
--	200-229:	c4xxx nims			%DNP%
			,npm-4000-fddi-sas(200)
			,npm-4000-fddi-das(201)
			,npm-4000-1e(202)
			,npm-4000-1r(203)
			,npm-4000-2s(204)
			,npm-4000-2e1(205)
			,npm-4000-2e(206)
			,npm-4000-2r1(207)
			,npm-4000-2r(208)
			,npm-4000-4t(209)
			,npm-4000-4b(210)
			,npm-4000-8b(211)
			,npm-4000-ct1(212)
			,npm-4000-ce1(213)
			,npm-4000-1a(214)
     	                ,npm-4000-6e-pci(215)
			,npm-4500-2t16s(216)		--%DNP%
			,npm-4000-1fe(217)
			,npm-4000-1hssi(218)
			,npm-4000-2e-pci(219)
			,npm-4000-4gb(220)			-- 4-Port Serial E1/G.703 
			,cat-4000-wsx-4712-qam24b(221)		-- Card with 12 ports, each having 2 QAM (Quadrature Amplitude Modulation)channels, based on ITU-T J.83 Annex B. %DNP% until Dec 2003, contact jalagar

--	230-259:	c4700 & VIP port adapters	%DNP%
			,pa-1fe(230)
			,pa-8e(231)
			,pa-4e(232)
			,pa-5e(233)
			,pa-4t(234)
			,pa-4r(235)
			,pa-fddi(236)
			,sa-encryption(237)
			,pa-ah1t(238)
			,pa-ah2t(239)
			,pa-a4t(240)			--%DNP%
			,pa-a8t-v35(241)
			,pa-1fe-tx-isl(242)
			,pa-1fe-fx-isl(243)
			,pa-1fe-tx-nisl(244)
			,sa-compression(245)
			,pa-atm-lite-1(246)
			,pa-ct3(247)
			,pa-oc3sm-mux-cbrt1(248)
			,pa-oc3sm-mux-cbr120e1(249)
			,pa-oc3sm-mux-cbr75e1(250)	--%DNP% project cancelled, can reuse assignment
			,pa-oc3mm-mux-cbrt1(251)	--%DNP% project cancelled, can reuse assignment
			,pa-oc3mm-mux-cbr120e1(252)	--%DNP% project cancelled, can reuse assignment
			,pa-oc3mm-mux-cbr75e1(253)	--%DNP% project cancelled, can reuse assignment
			,pa-ds3-mux-cbrt1(254)
			,pa-e3-mux-cbr120e1(255)
			,pa-e3sm-mux-cbr75e1(256)	--%DNP% project cancelled, can reuse assignment
			,pa-8b-st(257)
			,pa-4b-u(258)
			,pa-fddi-fd(259)
--	260-289:	MARs cards			%DNP%
			,pm-cpm-1e2w(260)
			,pm-cpm-2e2w(261)
			,pm-cpm-1e1r2w(262)
			,pm-ct1-csu(263)
			,pm-2ct1-csu(264)
			,pm-ct1-dsx1(265)
			,pm-2ct1-dsx1(266)
			,pm-ce1-balanced(267)
			,pm-2ce1-balanced(268)
			,pm-ce1-unbalanced(269)
			,pm-2ce1-unbalanced(270)
			,pm-4b-u(271)
			,pm-4b-st(272)
			,pm-8b-u(273)
			,pm-8b-st(274)
			,pm-4as(275)
			,pm-8as(276)
			,pm-4e(277)
			,pm-1e(278)
			,pm-4r(279)			--%DNP% project cancelled, contact scottb
			,pm-m4t(280)
			,pm-16a(281)
			,pm-32a(282)
			,pm-c3600-1fe-tx(283)
			,pm-c3600-compression(284)
			,pm-dmodem(285)
			,pm-8admodem(286)
			,pm-16admodem(287)
			,pm-c3600-1fe-fx(288)
			,pm-1fe-2t1-csu(289)		-- Port Module with 1 Fast Ethernet, 2 T1 with CSU
--	290-309:	as5200 cards			%DNP%
			,as5200-carrier(290)
			,as5200-2ct1(291)
			,as5200-2ce1(292)
			,as5200-dtd-carrier(293)
--	310-329:	as5200 port adapters		%DNP%
			,pm-as5xxx-12m(310)
			,pm-as5xxx-12m-56k(311)
			,pm-as5xxx-12m-v110(312)
--	330-359:	25xx cards			%DNP%
-- The expansions for some acronyms used in this section are given below:
--	CSU - Channel Service Unit
--	DSU - Dial Service Unit
--	FT1 - Fractional T1
--	WIC - Wan Interface Card
			,wm-c2500-5in1(330)
			,wm-c2500-t1-csudsu(331)
			,wm-c2500-sw56-2wire-csudsu(332)
			,wm-c2500-sw56-4wire-csudsu(333)
			,wm-c2500-bri(334)
			,wm-c2500-bri-nt1(335)
--	360-389:	16xx 26xx and 36xx cards	%DNP%
			,wic-serial-1t(360)
			,wic-serial-2t(361)
			,wic-csu-dsu-2(362)		--%DNP% Project cancelled, can reuse the assignment
			,wic-csu-dsu-4(363)
			,wic-s-t-3420(364)
			,wic-s-t-2186(365)
			,wic-u-3420(366)
			,wic-u-2091(367)
			,wic-u-2091-2081(368)
			,wic-s-t-2186-leased(369)
			,wic-t1-csudsu(370)		-- FT1 CSU/DSU Wan Interface Card 
			,wic-serial-2as(371)		-- WAN Interface Card - 2 port Async/Sync
			,aim-compression(372)		-- Compression Advanced Interface Module (AIM)
			,c3660-2fe-tx(373)		-- c3660 onboard 2FE(TX) version
			,pm-oc3mm(374)			-- ATM OC3 multimode Port Module
			,pm-oc3mm-vpd(375)		-- ATM OC3 multimode Port Module with Voice Processing Deck
			,pm-oc3smi-vpd(376)		-- ATM OC3 single mode intermediate reach Port Module with Voice Processing Deck
			,pm-oc3sml-vpd(377)		-- ATM OC3 single mode long reach Port Module with Voice Processing Deck
			,pm-oc3sml(378)			-- ATM OC3 single mode long reach Port Module
			,pm-oc3smi(379)			-- ATM OC3 single mode intermediate reach Port Module
			,pm-ima-4t1(380)		-- 4 port T1 IMA (Inverse Mux for ATM) port module %DNP% until Aug 99, contact jhayduk
			,pm-ima-8t1(381)		-- 8 port T1 IMA (Inverse Mux for ATM) port module %DNP% until Aug 99, contact jhayduk
			,pm-ima-4e1(382)		-- 4 port E1 IMA (Inverse Mux for ATM) port module %DNP% until Aug 99, contact jhayduk
			,pm-ima-8e1(383)		-- 8 port E1 IMA (Inverse Mux for ATM) port module %DNP% until Aug 99, contact jhayduk
			,nm-1fe-2w(384)			-- Network Module with 1 Fast Ethernet and 2 WIC/VIC interfaces
			,nm-2fe-2w(385)			-- Network Module with 2 Fast Ethernet and 2 WIC/VIC interfaces
			,nm-1fe-1r-2w(386)		-- Network Module with 1 Fast Ethernet, 1 token ring, and 2 WIC/VIC interfaces
			,nm-2w(387)			-- Network Module with 2 WIC/VIC interfaces
			,aim-encryption(388)		-- Encryption Advanced Interface Module for the c2600, c3620, c3640, and c3660 %DNP% until Aug 2000, contact jminer
			,c36xx-1fe-tx(389)		-- Onboard 1FE Interface for the c3660 chassis
--	400-429:	more c4700 & VIP port adapters	%DNP%
			,pa-jt2(400)
			,pa-posdw(401)
			,pa-4me1-bal(402)
			,pa-2ce1-balanced(403)
			,pa-2ct1(404)
			,pa-1vg(405)
			,pa-atmdx-ds3(406)
			,pa-atmdx-e3(407)
			,pa-atmdx-sml-oc3(408)
			,pa-atmdx-smi-oc3(409)
			,pa-atmdx-mm-oc3(410)
			,pa-possw(411)			-- Packet Over Sonet(POS) Single Wide Adapter Card %DNP% card obsoleted 
			,pa-a8t-x21(414)
			,pa-a8t-rs232(415)
			,pa-4me1-unbal(416)
			,pa-4r-fdx(417)
			,pa-1e3(418)
			,pa-2e3(419)
			,pa-1t3(420)
			,pa-2t3(421)
			,pa-2ce1-unbalanced(422)
			,pa-14e-switch(423)
			,pa-1fe-fx-nisl(424)
			,pa-esc-channel(425)
			,pa-par-channel(426)
			,pa-ge(427)			-- Gigabit Ethernet Port Adapter
			,pa-4ct1-csu(428)		-- 8 Port Channelized T1 with CSU 
			,pa-8ct1-csu(429)		-- 8 Port Channelized T1 with CSU
--	430-459:	c38xx cards			%DNP%
			,c3800-vdm(430)
			,c3800-vdm-dc-2t1e1(431)
			,c3800-vdm-dc-1t1e1-enet(432)
			,pa-2feisl-tx(433)
			,pa-2feisl-fx(434)
			,mc3810-dcm(435)
			,mc3810-mfm-e1balanced-bri(436)
			,mc3810-mfm-e1unbalanced-bri(437)
			,mc3810-mfm-e1-unbalanced(438)
			,mc3810-mfm-dsx1-bri(439)
			,mc3810-mfm-dsx1-csu(440)
			,mc3810-vcm(441)	
			,mc3810-avm(442)
			,mc3810-avm-fxs(443)
			,mc3810-avm-fxo(444)
			,mc3810-avm-em(445)
			,mc3810-vcm3(446)		-- MC3810 Voice Compression Module with 3 DSPs (Digital Signal Processor) 
			,mc3810-bvm(447)		-- MC3810 Basic Voice Module
			,mc3810-avm-fxo-uk(448)		-- MC3810 Analog Voice Module UK Foreign eXchange Office
			,mc3810-avm-fxo-ger(449)	-- MC3810 Analog Voice Module Germany Foreign eXchange Office
			,mc3810-hcm2(450)		-- MC3810 High (Voice) Compression Module with 2 DSPs (Digital Signal Processor)
			,mc3810-hcm6(451)		-- MC3810 High (Voice) Compression Module with 6 DSPs (Digital Signal Processor) 
			,mc3810-avm-fxo-pr3(452)	-- MC3810 Analog Voice Module Singapore or Japan Foreign eXchange Office
			,mc3810-avm-fxo-pr2(453)	-- MC3810 Analog Voice Module Australia or New Zealand Foreign eXchange Office
			,mc3810-vdm(454)		-- MC3810 Video Dial-up Module
			,mc3810-apm-fxs-did(455)	-- MC3810 Foreign Exchange Station (FXS) Direct Inward Dialing (DID) Analog Personality Module
			,mc3810-bvm-nt-te(456)		-- 4 ports NT or TE BRI Voice Module on MC3810
			,mc3810-hcm1(457)		-- High performance compression module for the MC3810 platform equipped with one TI 549 DSP
			,mc3810-hcm3(458)		-- High performance compression module for the MC3810 platform equipped with three TI 549 DSPs
			,mc3810-hcm4(459)		-- High performance compression module for the MC3810 platform equipped with four TI 549 DSPs
--	460-479:	as5300 port modules		%DNP%
-- 460 available
			,pm-dtd-6m(461)
			,pm-dtd-12m(462)		-- mica 12 modem module 
--	480-499:	as5300 cards			%DNP%
			,as5300-4ct1(480)
			,as5300-4ce1(481)
			,as5300-carrier(482)
			,as5300-compression(483)	--%DNP% project cancelled, can reuse assignment
			,as5300-dtd-carrier(484)
			,as5300-8ct1-4t(485)		-- Channelized octal T1 and 4 serial card
			,as5300-8ce1-4t(486)		-- Channelized octal E1 and 4 serial card
			,as5300-4ct1-4t(487)		-- Channelized quad T1 and 4 serial card
			,as5300-4ce1-4t(488)		-- Channelized quad E1 and 4 serial card
			,as5300-amazon2-carrier(489)	-- Amazon II mica carrier card
--	500-529:	voice cards			%DNP%
			,vic-em(500)
			,vic-fxo(501)
			,vic-fxs(502)
			,vpm-2v(503)
			,vpm-4v(504)
			,dsp-vfc30(505)
			,dsp-vfc24(506)			--%DNP% project cancelled, can reuse assignment
			,dspm-c542(507)			-- DSP (Digital Signal Processor) C542  module for the AS5300 and AS5800 series
			,vic-2fxo-eu(508)		-- 2 port Foreign eXchange Office Voice Interface Cards for most of Europe 
			,vic-2fxo-m3(509)		-- 2 port Foreign eXchange Office Voice Interface Cards for Australia 
			,vic-2fxo-m4(510)		-- 2 port Foreign eXchange Office Voice Interface Cards for Germany
			,vic-2fxo-m5(511)		-- 2 port Foreign eXchange Office Voice Interface Cards for France
			,vic-2fxo-m6(512)		-- 2 port Foreign eXchange Office Voice Interface Cards for Italy
			,vic-2fxo-m7(513)		-- 2 port Foreign eXchange Office Voice Interface Cards for Portugal
			,vic-2fxo-m8(514)		-- 2 port Foreign eXchange Office Voice Interface Cards for Singapore 
			,vic-2st-2086(515)		-- 2 port Terminal Endpoint BRI S/T Voice interface daughter card
			,hdv(516)                       -- High Density Voice over IP network module
			,dspm-6c549(517)		-- DSP (Digital Signal Processor) module that contains 6 C549 DSPs, used in AS5300 and AS5800
			,wvic-1dsu-t1(518)-- WAN Voice Interface Card with a single port T1 DSU for 1600, 1700, 2600, or 3600 series %DNP% until Aug 99, contact kijewski
			,wvic-1dsu-e1(519)		-- WAN Voice Interface Card with a single port E1 DSU for 1600, 1700, 2600, or 3600 series %DNP% until Aug 99, contact kijewski
			,wvic-2dsu-t1(520)		-- WAN Voice Interface Card with a dual port T1 DSU for 1600, 1700, 2600, or 3600 series %DNP% until Aug 99, contact kijewski
			,wvic-2dsu-e1(521)		-- WAN Voice Interface Card with a dual port E1 DSU for 1600, 1700, 2600, or 3600 series %DNP% until Aug 99, contact kijewski
			,wvic-2dsu-t1-di(522)		-- WAN Voice Interface Card with a dual port T1 DSU with Drop and Insert for 1600, 1700, 2600, or 3600 series %DNP% until Aug 99, contact kijewski
			,wvic-2dsu-e1-di(523)           -- WAN Voice Interface Card with a dual port E1 DSU with Drop and Insert for 1600, 1700, 2600, or 3600 series %DNP% until Aug 99, contact kijewski
			,as-mica-dspm-c5x(524)		-- MICA module with C5x DSP processor that is modem and voice capable, for the ASxxxx chassis %DNP% until Jan 2000, contact deli	
			,vic-2fxo-m2(525)		-- 2 port Foreign eXchange Office Voice Interface Cards (Module 2) for Europe/Australia/New Zealand
			,vic-16fxs(526)			-- 16 Port FXS Voice Interface Module %DNP% until Jul 2000, contact tommy-proj-team
			,vic-8fxs(527)			-- 8 Port FXS Voice Interface Module %DNP% until Jul 2000, contact tommy-proj-team
			,hda-nm-4fxs(528)		-- High Density Analog Voice Module 

--	530-559:	BFR cards			%DNP%
			,pos-qoc3-mm(530)
			,pos-qoc3-sm(531)
			,pos-oc12-mm(532)
			,pos-oc12-sm(533)
			,atm-oc12-mm(534)
			,atm-oc12-sm(535)
			,pos-oc48-mm-l(536)
			,pos-oc48-sm-lr-fc(537)		-- GSR 1 port Packet Over Sonet OC-48, single mode, long reach, FC connector card
			,gsr-sfc(538)
			,gsr-csc(539)
			,gsr-csc4(540)
			,gsr-csc8(541)
			,gsr-sfc8(542)
			,atm-qoc3-sm(543)               -- Quad OC3 Line Card ATM Singlemode Fiber Ports
			,atm-qoc3-mm(544)               -- Quad OC3 Line Card ATM Multimode Fiber Ports
			,gsr-oc12chds3-mm(545)		-- OC12 channelised to DS3 multimode
			,gsr-oc12chds3-sm(546)		-- OC12 channelised to DS3 singlemode
			,gsr-1ge(547)			-- GSR 1 Port Gigabit Ethernet Line Card 
			,gsr-oc12chsts3-mm(548)		-- GSR OC12 channelized to STS-3c/STM-1 multi-mode line card
			,gsr-oc12chsts3-sm(549)		-- GSR OC12 channelized to STS-3c/STM-1 single-mode line card
			,gsr-qoc12-mm(550)		-- GSR Four Port OC12c/STM-4c Multi-mode ATM Card %DNP% until Aug 99, contact stevmars
			,gsr-qoc12-sm(551)		-- GSR Four Port OC12c/STM-4c Single-Mode ATM Card %DNP% until Aug 99, contact stevmars
			,pos-oc48-sm-sr-fc(552)		-- GSR 1 Port Packet Over SONET OC-48c/STM-16 Single Mode Short Reach with FC connector
			,pos-qoc3-sm-l(553)		-- GSR 4 Port Packet Over SONET OC-3c/STM-1 Single Mode Long Reach
			,pos-8oc3-mm(554)		-- GSR 8 port OC3 Multimode POS %DNP% until Sep 99, contact esu
			,pos-8oc3-ir(555)		-- GSR 8 port OC3 SM intermediate reach POS %DNP% until Sep 99, contact esu
			,pos-8oc3-lr(556)		-- GSR 8 port OC3 SM long reach POS %DNP% until Sep 99, contact esu
			,pos-16oc3-mm(557)		-- GSR 16 port OC3 multimode POS %DNP% until Sep 99, contact esu
			,pos-16oc3-ir(558)		-- GSR 16 port OC3 SM intermediate reach POS %DNP% until Sep 99, contact esu
			,pos-16oc3-lr(559)		-- GSR 16 port OC3 SM long reach POS %DNP% until Sep 99, contact esu
--	560-599:	more c4700 & VIP port adapters	%DNP%
			,pa-8ct1(560)			-- 8 Port Channelized T1
			,pa-8ce1(561)			-- 8 Port Channelized E1
			,pa-ce3(562)			-- Channelized E3 Port Adapter
			,pa-4r-dtr(563)			-- 4 port Dedicated Token Ring port adapter 
			,pa-possw-sm(564)		-- Single Width POS (Packet Over Sonet) Port Adapter with Singlemode Fiber
			,pa-possw-mm(565)		-- Single Width POS (Packet Over Sonet) Port Adapter with Multimode Fiber
			,pa-possw-lr(566)		-- Single Width POS (Packet Over Sonet) Port Adapter with Long Range Fiber
			,pa-1t3-plus(567)		-- Improved one port serial T3 plus port adapter
			,pa-2t3-plus(568)		-- Improved 2 port serial T3 plus port adapter
			,pa-ima-t1(569)			-- Implements IMA functionality for the 7200/7500 platform for a T1
			,pa-ima-e1(570)			-- Implements IMA functionality for the 7200/7500 platform for an E1
			,pa-2ct1-csu(571)		-- 2 port multichannel T1 port adapter with built in csu/dsu for the 7200, 7500, and rsp7000 platforms
			,pa-2ce1(572)			-- 2 port multichannel E1 port adapter for the 7200, 7500, and rsp7000 platforms 
			,pa-2fe-tx(573)			-- 2-port FastEthernet port adapter with two RJ-45 interfaces %DNP% until Sep 2000, contact vsuri
			,pa-2fe-fx(574)			-- 2-port FastEthernet port adapter with two multi-mode fiber interfaces %DNP% until Sep 2000, contact vsuri
			,pa1-esc4-channel(575)		-- High Performance ESCON Channel Port Adapter Version 4 
			,pa2-oc3-pos-sw(576)		-- Dual Port OC-3c Packet Over Sonet(POS) Single Wide Adapter Card
			,pa-4dtr(577)			-- Four port dedicated tokenring adapter
			,pa-vm-hda-8fxs-did(578)	-- High density analog voice/fax voice module with 8 FXS/DID

--	600-629:	more MARS cards			%DNP%
			,pm-1fe-1t1(600)		-- Port Module with 1 Fast Ethernet, 1 T1
			,pm-1fe-2t1(601)		-- Port Module with 1 Fast Ethernet, 2 T1
			,pm-1fe-1e1(602)		-- Port Module with 1 Fast Ethernet, 1 E1
			,pm-1fe-2e1(603)		-- Port Module with 1 Fast Ethernet, 2 E1
			,pm-1fe-1t1-csu(604)            -- Port Module with 1 Fast Ethernet, 1 T1 with CSU 
			,pm-atm25(605)			-- 25 Mbits/sec ATM Port Module
			,pm-hssi(606)			-- HSSI Card Port Module 
--	630-649:	Nitro cards			%DNP%
			,as5800-dsc(630)
			,as5800-12t1(631)
			,as5800-12e1(632)
			,as5800-mica-hmm(633)
			,as5800-t3(634)			-- T3 trunk card
			,as5800-1fe-dsi(635)
			,as5800-mica-dmm(636)		-- Mica Double density Modem Module
			,as5800-vcc(637)		-- Voice Carrier Card for the AS5800
			,as5800-dspm-6c549(638)		-- Digital Signal Processor Module with 6 C549's Voice Feature Card for the AS5800
			,as5800-dsp(639)		-- Digital Signal Processor Voice Feature Card for the AS5800
			,as5800-vccmc(640)		-- Medium Complexity Voice Carrier Card %DNP% until Oct 2000, contact kevhuynh
--	650-699:	c6xxx cards
			,slc-cap8(650)			-- Subscriber line card for c6200 - Carrierless Amplitude and Phase modulation - 8 port variation 
			,ntc-oc3si(651)			-- Network Trunk card for c6200 - Optical Carrier 3, single-mode, intermediate reach variation
			,ntc-oc3mm(652)			-- Network Trunk card for c6200 -  Optical Carrier 3, multi-mode reach variation
			,ntc-stm1si(653)		-- Network Trunk card for c6200 - Synchronous Transport Module level 1, single-mode, intermediate reach variation 
			,ntc-stm1mm(654)		-- Network Trunk card for c6200 - Synchronous Transport Module level 1, multi-mode variation
			,slc-dmt8(655)			-- Subscriber line card for c6200 - Discrete Multi-Tone 8 port variation
			,slc-dmt16(656)			-- Subscriber line card for c6200 - Discrete Multi-Tone 16 port variation
			,ntc-ds3(657)			-- Network Trunk card for c6200 - DS3
			,wsx-6182-2pa(658)		-- Flex-Wan line card for Catalyst 6xxx - 2-WAN PA line card ws-x6182-2pa %DNP% until Feb 2000, contact dperez
			,osm-1oc48-pos-ss(659)		-- Optical Service Module, 1-Port OC48 POS SS w/ 4 GE
			,osm-1oc48-pos-sl(660)		-- Optical Service Module, 1-Port OC48 POS SL w/ 4 GE
			,osm-1oc48-pos-si(661)		-- Optical Service Module, 1-Port OC48 POS SI w/ 4 GE
			,osm-2oc12-atm-si(662)		-- Optical Service Module, 2-Port OC12 ATM SI w/ 4 GE %DNP% until May 2001, contact dperez
			,osm-2oc12-atm-mm(663)		-- Optical Service Module, 2-Port OC12 ATM MM w/ 4 GE %DNP% until May 2001, contact dperez
			,osm-2oc12-pos-sl(664)		-- Optical Service Module, 2-Port OC12 POS SL w/ 4 GE
			,osm-4oc12-pos-sl(665)		-- Optical Service Module, 4-Port OC12 POS SL w/ 4 GE
			,osm-2oc12-pos-mm(666)		-- Optical Service Module, 2-Port OC12 POS MM w/ 4 GE
			,osm-4oc12-pos-mm(667)		-- Optical Service Module, 4-Port OC12 POS MM w/ 4 GE
			,osm-2oc12-pos-si(668)		-- Optical Service Module, 2-Port OC12 POS SI w/ 4 GE
			,osm-4oc12-pos-si(669)		-- Optical Service Module, 4-Port OC12 POS SI w/ 4 GE
			,osm-8oc3-pos-si(670)		-- Optical Service Module, 8-Port OC3 POS SI w/ 4 GE
			,osm-16oc3-pos-si(671)		-- Optical Service Module, 16-Port OC3 POS SI w/ 4 GE
			,osm-8oc3-pos-mm(672)		-- Optical Service Module, 8-Port OC3 POS MM w/ 4 GE
			,osm-16oc3-pos-mm(673)		-- Optical Service Module, 16-Port OC3 POS MM w/ 4 GE
			,osm-8oc3-pos-sl(674)		-- Optical Service Module, 8-Port OC3 POS SL w/ 4 GE
			,osm-16oc3-pos-sl(675)		-- Optical Service Module, 16-Port OC3 POS SL w/ 4 GE
			,osm-4ge-wan-gbic(676)		-- Optical Service Module, 4-Port GE w/ WAN services
			,osm-4ge-4oc3-pos-sm-ir(677)	-- Optical Service Module, 4 port OC3 pos, Singlemode, Intermediate Range with 4 Gigabit Ethernet ports %DNP% until Nov 2001, contact vkamma
			,osm-4ge-4oc3-pos-mm-sr(678)	-- Optical Service Module, 4 port OC3 pos, Multimode, Short Range with 4 Gigabit Ethernet ports %DNP% until Nov 2001, contact vkamma
			,osm-4ge-4oc3-pos-sm-lr(679)	-- Optical Service Module, 4 port OC3 POS, Singlemode, Long Range with 4 Gigabit Ethernet ports %DNP% until Nov 2001, contact vkamma
			,osm-4ge-4oc12-chds3-sm-ir(680)	-- Optical Service Module, 4-Port OC12 channelized down to DS3 Singlemode Intermediate range with 4 GE
			,osm-4ge-8oc12-chds3-sm-ir(681) -- Optical Service Module, 8-Port OC12 channelized down to DS3 Singlemode Intermediate range with 4 GE
			,osm-4ge-oc48-chds3-sm-sr(682)	-- Optical Service Module, 1-Port OC48 channelized down to DS3 Singlemode Short range with 4 GE
			,osm-4ge-2oc48-chds3-sm-sr(683)	-- Optical Service Module, 2-Port 0C48 channelized down to DS3 Singlemode Short range with 4 GE
			,osm-4ge-oc48-chds3-sm-ir(684)	-- Optical Service Module, 1-Port OC48 channelized down to DS3 Singlemode Intermediate range with 4 GE
			,osm-4ge-2oc48-chds3-sm-ir(685)	-- Optical Service Module, 2-Port OC48 channelized down to DS3 Singlemode Intermediate range with 4 GE
			,osm-4ge-oc12-chds3-sm-ir(686)	-- Optical Service Module, 1-Port OC12 channelized down to DS3 Single Mode Intermediate range with 4 GE
			,osm-4ge-2oc12-chds3-sm-ir(687)	-- Optical Service Module, 2-Port OC12 channelized down to DS3 Single Mode Intermediate range with 4 GE
			,mwam-blade(688)		-- Multiprocessor WAN Application Module - a multipurpose blade for the Cat65xx platform %DNP% until Sep 2002, contact chrisl

--	700-749:	Milan cards			%DNP%
			,c9000Fabric13Port(700)		-- Catalyst 9000 series 13 port crossbar switching fabric %DNP% until Jan 2000, contact cls.
			,c9000SMC(701)			-- Catalyst 9000 series SMC system management card %DNP% until Jan 2000, contact cls.
			,c9000RMC(702)			-- Catalyst 9000 series RMC rmon processor module %DNP% until Jan 2000, contact cls.
			,c9000-24xfe(703)		-- Catalyst 9000 series 24 port 10/100MB ethernet  %DNP% until Jan 2000, contact cls.
			,c9000-32xfe(704)		-- Catalyst 9000 series 32 port 10/100MB ethernet  %DNP% until Jan 2000, contact cls.
			,c9000-8xge(705)		-- Catalyst 9000 series 8 port 1000MB ethernet %DNP% until Jan 2000, contact cls.
--	750-799:	rpm cards			%DNP%
			,atmdx-rpm(750)			-- RPM Cell Bus Interface
--      800-849:        more VIP port adapters          %DNP%
			,pa-vxc-2t1e1(800)		-- 2 port T1/E1 voice port adapter with 30 DSP's %DNP% until Sep 99, contact dkhurana
			,pa-vxb-2t1e1(801)		-- 2 port T1/E1 voice port adapter with 12 DSP's %DNP% until Sep 99, contact dkhurana 
			,pa-atm-oc12-mm(802)		-- Multimode ATM OC-12 Port Adapter 
			,pa-atm-oc12-smi(803)		-- Singlemode ATM OC-12 Intermediate reach Port Adapter 
			,pa-mct3(804)			-- Multichannel DS3 single port adapter
			,pa-mc2t3(805)			-- Multichannel DS3 dual port adapter
			,pa-pos-oc12-mm(806)		-- OC-12 Packet Over SONET Port Adapter, Multi-Mode fiber
			,pa-pos-oc12-sm(807)		-- OC-12 Packet Over SONET Port Adapter, Single Mode fiber
			,srp-pa-oc12-mm(808)		-- SRP OC-12/STM-4 Multimode Port Adapter for 7000 series
			,srp-pa-oc12-sm-ir(809)		-- SRP OC-12/STM-4 Single Mode Intermediate Reach Port Adapter for 7000 series
			,srp-pa-oc12-lr(810)		-- SRP OC-12/STM-4 Single Mode Long Reach Port Adapter for 7000 series
			,pa-mcx-2te1(811)		-- 2 port, software configurable Multichannel T1/E1 with TDM Port Adapter
			,pa-mcx-4te1(812)		-- 4 port, software configurable Multichannel T1/E1 with TDM Port Adapter
			,pa-mcx-8te1(813)		-- 8 port, software configurable Multichannel T1/E1 with TDM Port Adapter
			,srp-pa-oc12-sm-xr(814)	-- SRP OC-12/STM-4 Single Mode Extended Reach Port Adapter for 7000 series
			,pa-vxc-2t1e1-plus(815)		-- 2 port, T1/E1 voice PA+ with 30 DSPs %DNP% until Jul 2000, contact hsiang
			,pa-vxb-2t1e1-plus(816)		-- 2 port, T1/E1 voice PA+ with 12 DSPs %DNP% until Jul 2000, contact hsiang
			,pa-mc-stm1-smi(817)		-- channelized STM-1 PA for 7500/7200(single mode intermediate reach) %DNP% until Nov 2000, contact czheng
			,pa-mc-stm1-mm(818)		-- channelized STM-1 PA for 7500/7200(multimode) %DNP% until Nov 2000, contact czheng
			,pa-dual-wide-ge(819)		-- Dual Wide Enhanced Gigabit Ethernet Port Adapter
			,pa-vxa-1t1e1-24(820)		-- 1 port T1/E1 voice port adapter w/ 7 DSPs
			,pa-vxa-1t1e1-30(821)		-- 1 port T1/E1 voice port adapter w/ 8 DSPs
			,pa-mc-8t1e1(822)		-- Multichannel T1/E1 (without TDM) Port Adapter
			,pa-san-fc1(823)                -- Storage Area Network, single E_Port Fibre Channel over Internet Protocol(FCIP) PA %DNP% until Apr 2002, contact fxu, tjw, fchao
			,pa-mcx-8te1-m(824)		-- 8 port, software configurable Multichannel T1/E1 SS7 with TDM Port Adapter
--	850-899:	Wide Area Switch common cards (MGX, IGX series boxes)	%DNP%
			,ausm-8t1(850)			-- ATM User Network Interface Service Module with 8 T1 ports
			,ausm-8e1(851)			-- ATM User Network Interface Service Module with 8 E1 ports
			,cesm-8t1(852)			-- Circuit Emulation Service Module with 8 T1 ports
			,cesm-8e1(853)			-- Circuit Emulation Service Module with 8 E1 ports
			,frsm-8t1(854)			-- Frame Relay Service Module with 8 T1 ports
			,frsm-8e1(855)			-- Frame Relay Service Module with 8 E1 ports
			,frsm-4x21(856)			-- Frame Relay Service Module supporting 4 high speed X.21 ports
			,frsm-2hssi(857)		-- Frame Relay Service Module supporting 2 high speed HSSI ports
			,cesm-1t3(858)			-- Circuit Emulation Service Module (CESM) with one T3 port
			,cesm-1e3(859)			-- Circuit Emulation Service Module (CESM) with one E3 port
			,vism-8t1(860)			-- Voice Interworking Service Module (VISM) with 8 T1 ports
			,vism-8e1(861)			-- Voice Interworking Service Module (VISM) with 8 E1 ports
			,mgx-rpm(862)			-- MGX8800 Route Processor Module having the functionality of a C7200 router
			,mgx-srm-3t3(863)		-- MGX8800 Service Redundancy Module supporting 3 T3 ports on back card, used for providing 1:N redundancy for T1 modules
			,enh-axsm-1oc12(864)		-- AXSM-1-622-E Enhanced ATM Switch Service Module, 1 Port, OC12c/STM-4 compliant %DNP% until Jan 2000, contact sshegde
			,enh-axsm-2oc12(865)		-- AXSM-2-622-E Enhanced ATM Switch Service Module, 2 Port, OC12c/STM-4 compliant %DNP% until Jan 2000, contact sshegde
			,enh-axsm-4oc3(866)		-- AXSM-4-155-E Enhanced ATM Switch Service Module, 4 Ports, OC3c/STM-1 compliant %DNP% until Jan 2000, contact sshegde
			,enh-axsm-8oc3(867)		-- AXSM-8-155-E Enhanced ATM Switch Service Module, 8 Ports, OC3c/STM-1 compliant %DNP% until Jan 2000, contact sshegde
			,enh-axsm-4stm1(868)		-- AXSM-4-155-E Enhanced ATM Switch Service Module, 4 Ports, STM-1 Electrical %DNP% until Jan 2000, contact sshegde
			,enh-axsm-8stm1(869)		-- AXSM-8-155-E Enhanced ATM Switch Service Module, 8 Ports, STM-1 Electrical %DNP% until Jan 2000, contact sshegde
			,enh-axsm-8t3e3(870)		-- Enhanced ATM Switch Service Module, 8 T3/E3 Ports %DNP% until Jan 2000, contact sshegde
			,enh-axsm-16t3e3(871)		-- Enhanced ATM Switch Service Module, 16 T3/E3 Ports %DNP% until Jan 2000, contact sshegde
			,enh-axsm-8t1(872)		-- Enhanced ATM Switch Service Module, 8 T1 Ports and IMA Support %DNP% until Jan 2000, contact sshegde
			,enh-axsm-16t1(873)		-- Enhanced ATM Switch Service Module, 16 T1 Ports and IMA Support %DNP% until Jan 2000, contact sshegde
			,enh-axsm-8e1(874)		-- Enhanced ATM Switch Service Module, 8 E1 Ports and IMA Support %DNP% until Jan 2000, contact sshegde
			,enh-axsm-16e1(875)		-- Enhanced ATM Switch Service Module, 16 E1 Ports and IMA Support %DNP% until Jan 2000, contact sshegde
			,axsm-2oc12(876)		-- AXSM-2-622 ATM Switch Service Module(AXSM), 2 Port OC12 Compliant %DNP% until May 2000, contact subrah
			,mgx-xm60(877)		-- Cross Bar Switch Module supported in selected MGX Series chassis %DNP% until Jul 2000, contact subrah
			,mgx-rpm-pr(878)	-- Router Processor Module(RPM) Premium in selected MGX Series %DNP% until Apr 2001, contact suhail
			,axsm-1oc48b(879)		-- AXSM-1-2488/B ATM Switch Service Module(AXSM), 1 Port OC48 Compliant %DNP% until Aug 2000, contact subrah
			,axsm-4oc12b(880)		-- AXSM-4-622/B ATM Switch Service Module(AXSM), 4 Port Oc12 compliant %DNP% until Aug 2000, contact subrah
			,axsm-16oc3b(881)		-- AXSM-16-155/B ATM Switch Service Module(AXSM), 16 Port Oc3 compliant %DNP% until Aug 2000, contact subrah
			,axsm-c-12t3(882)		-- AXSM-C 12 port T3 module is a Channelized ATM Service Module %DNP% until Jul 2001, contact rli
			,vixm-4oc12(883) 		-- Voice Interworking Switching Module(VIXM) 4 port OC12 card %DNP% until Sep 2001, contact khiremat
			,vixm-16oc3(884) 		-- Voice Interworking Switching Module(VIXM) 16 port OC3 card %DNP% until Sep 2001, contact khiremat
			,mgx-rpm-xf(885)		-- Router Processor Module Express Forwarding in select MGX series and Jupiter Chassis %DNP% until Nov 2001, contact bkundass
			,cesmb-8e1(886)		-- Circuit Emulation Service Module B (CESN/B) with 8 E1 ports %DNP% until Jan 2002, contact wwcai
			,cesmb-8t1(887)		-- Circuit Emulation Service Module B (CESN/B) with 8 T1 ports %DNP% until Jan 2002, contact wwcai
			,frsmc-8e1(888)		-- Frame Relay Service Module C (FRSM/C) with 8 E1 ports %DNP% until Jan 2002, contact wwcai
			,frsmc-8t1(889)		-- Frame Relay Service Module C (FRSM/C) with 8 T1 ports %DNP% until Jan 2002, contact wwcai
			,frsmb-2hssi(890)	-- Frame Relay Service Module B (FRSM/B) with 2 hssi ports %DNP% until Jan 2002, contact wwcai
			,frsmb-12in1(891)	-- Frame Relay Service Module B (FRSM/B) with 12 In1 %DNP% until Jan 2002, contact wwcai
			,hsfr-12t3(892)		-- High Speed Frame Relay Service Module with 12 T3 ports %DNP% until Jan 2002, contact wwcai
			,hsfr-12e3(893)		-- High Speed Frame Relay Service Module with 12 E3 ports %DNP% until Jan 2002, contact wwcai
			,frsm-12t3(894)		-- Frame Relay Service Module, 12 T3 ports %DNP% until Jan 2002, contact wwcai
			,frsm-12e3(895)		-- Frame Relay Service Module, 12 E3 ports %DNP% until Jan 2002, contact wwcai
			,frsmb-2t3(896)		-- Frame Relay Service Module B (FRSM/B) with 2 T3 ports %DNP% until Jan 2002, contact wwcai
			,frsm-12t3e3(897)	-- Frame Relay Service Module with 12 T3/E3 ports %DNP% until Oct 2001, contact ramkuma wwcai
			,frsm-b2e3(898)		-- Frame Relay Service Module B (FRSM/B) with 2 E3 ports %DNP% until Jan 2002, contact wwcai
			,vism-pr-8t1(899)	-- Voice Interworking Service Module Premium Card (VISM-PR)with 8 T1 ports
--      900-949:        Catalyst 2900XL series cards    %DNP%
			,wsx-2914(900)			-- 4 port 10/100BaseTX module for Catalyst 2900XL series
			,wsx-2922(901)			-- 2 port 100BaseFX module for Catalyst 2900XL series
			,wsx-2914-v(902)		-- 4 port 10/100BaseTX ISL module for Catalyst 2900XL series
			,wsx-2922-v(903)		-- 2 port 100BaseFX ISL module for Catalyst 2900XL series
			,wsx-2924-v(904)		-- 4 port 100BaseFX module for Catalyst 2900XL series
			,wsx-2951(905)			-- ATM UTP module for Catalyst 2900XL series
			,wsx-2961(906)			-- ATM MMF module for Catalyst 2900XL series
			,wsx-2971(907)			-- ATM SMF-MR module for Catalyst 2900XL series
			,wsx-2972(908)			-- ATM SMF-LR module for Catalyst 2900XL series
			,wsx-2931(909)			-- GBIC Gigabit module for Catalyst 2900XL series
			,wsx-2932-xl(910)		-- 1000 Base-T Gigabit module for Catalyst 2900XL series %DNP% until Mar 2000, contact mdjoshi
			,mgbic-1000base-lh(911)		-- longhaul multimode fiber gigabit ethernet port adapter %DNP% until Apr 2002, contact shkumar
			,mgbic-1000base-zx(912)		-- extended reach singlemode fiber gigabit ethernet port adapter %DNP% until Apr 2002, contact shkumar
			,mgbic-1000base-cxstack(913)	-- Cisco gigaStack gigabit ethernet port adapter %DNP% until Apr 2002, contact shkumar
			,mgbic-1000baset(914)		-- Copper Unshielded twisted pair gigabit ethernet port adapter %DNP% until Apr 2002, contact shkumar
--	950-999:	Wide Area Switch Back Cards (also known as Line Modules)	%DNP%
			,lm-bnc-2t3(950)		-- Two T3 75-ohm BNC back card
			,lm-bnc-2e3(951)		-- Two E3 75-ohm BNC back card
			,lm-db15-4x21(952)		-- Four X.21 DB-15 back card
			,lm-scsi2-2hssi(953)		-- Two HSSI SCSI-2 back card
			,lm-rj48-8t1(954)		-- Eight T1 RJ48 back card
			,lm-rj48-8t1-r(955)		-- Eight T1 RJ48 redundancy back card
			,lm-rj48-8e1(956)		-- Eight E1 RJ48 back card
			,lm-rj48-8e1-r(957)		-- Eight E1 RJ48 redundancy back card
			,lm-smb-8e1(958)		-- Eight E1 SMB back card
			,lm-smb-8e1-r(959)		-- Eight E1 SMB redundancy back card
			,lm-psm-ui(960)			-- User Interface back card containing 2 RS-232 ports and one ethernet port, T1/E1 timing reference ports for Processor Switch Modules
			,lm-mmf-4oc3(961)		-- 4 port 155Mbps back card, MMF, SC connectors
			,lm-smfir-4oc3(962)		-- 4 port 155Mbps back card, SMF-IR, SC connectors
			,lm-smflr-4oc3(963)		-- 4 port 155Mbps back card, SMF-LR, SC connectors
			,lm-smfir-1oc12(964)		-- 1 port 622Mbps back card, SMF-IR, FC connectors
			,lm-smflr-1oc12(965)		-- 1 port 622Mbps back card, SMF-LR, FC connectors
			,lm-s3-ui(966)			-- Processor Switch Module (PXM) Stratum 3 User Interface back card for PXM1 or PXM2
			,lm-1fe-tx(967)			-- 1 port Fast Ethernet RJ45 connector back card for MGX8800 RPM module
			,lm-1fe-fx(968)			-- 1 port Fast Ethernet MMF connector back card for MGX8800 RPM module
			,lm-1mmf-fddi(969)		-- 1 port FDDI MMF connector back card for MGX8800 RPM module
			,lm-1smf-fddi(970)		-- 1 port FDDI SMF connector back card for MGX8800 RPM module
			,lm-rj45-4e(971)		-- 4 port Ethernet (10BaseT) RJ45 connector back card for MGX8800 RPM module
			,lm-mmf-8oc3(972)		-- 8 port 155Mbps back card, MMF, Small Form Factor MT-RJ connectors %DNP% until Nov 99, contact sshegde
			,lm-smf-ir-8oc3(973)		-- 8 port 155Mbps back card, SMF-IR, Small Form Factor MT-RJ connectors %DNP% until Nov 99, contact sshegde
			,lm-smf-lr-8oc3(974)		-- 8 port 155Mbps back card, SMF-LR, Small Form Factor MT-RJ connectors %DNP% until Nov 99, contact sshegde
			,lm-smf-ir-1oc48(975)		-- 1 port 2488Mbps back card, SMF-IR, FC connector %DNP% until Jan 2000, contact sshegde
			,lm-smf-lr-1oc48(976)		-- 1 port 2488Mbps back card, SMF-LR, FC connector %DNP% until Jan 2000, contact sshegde
			,lm-psm-hd(977)			-- Hard Disk back card for Processor Service Module %DNP% until Nov 99, contact sshegde
			,lm-smb-8t3(978)		-- 8 port T3 back card, SMB connector %DNP% until Feb 2000, contact sshegde
			,lm-smb-8e3(979)		-- 8 port E3 back card, SMB connector %DNP% until Feb 2000, contact sshegde
			,lm-smb-4stm1(980)		-- 4 port 155-mbps Electrical Back Card, SMB Connector %DNP% until Feb 2000, contact sshegde
			,lm-smf-ir-2oc12(981)		-- 2 Port 622-Mbps Back card SMF-IR %DNP% until May 2000, contact subrah
			,lm-smf-lr-2oc12(982)		-- 2 Port 622-Mbps Back card SMF-LR %DNP% until May 2000, contact subrah
			,lm-smf-sr-1oc48(983)		--  1 Port 2488-Mbps, Short Reach(SR), SMF-SR back card %DNP% until May 2000, contact subrah
			,lm-smf-xlr-1oc48(984)		--  1 Port 2488-Mbps, Extended Long Reach(XLR), SMF-XLR back card %DNP% until May 2000, contact subrah
			,lm-bnc-3t3(985)		--  3 T3  Back Card , BNC Connector
			,lm-smf-ir-1oc48b(986)		-- 1 Port 2488-Mbps, SMF-IR(Intermediate Reach) Back card Version B, SC Connector %DNP% until Aug 2000, contact subrah
			,lm-smf-lr-1oc48b(987)		-- 1 Port 2488-Mbps, SMF-LR (Long reach )Back card Version B, SC Connector %DNP% until Aug 2000, contact subrah
			,lm-smf-sr-1oc48b(988)		-- 1 Port 2488-Mbps, SMF-SR (Short Reach) Back card Version B, SC Connector %DNP% until Aug 2000, contact subrah
			,lm-smf-ir-2oc12b(989)		-- 2 Port 622-Mbps, SMF-IR(Intermediate reach) Back card Version B, SC Connector %DNP% until Aug 2000, contact subrah
			,lm-smf-lr-2oc12b(990)		-- 2 Port 622-Mbps, SMF-LR(Long reach) Back card Version B, SC Connector %DNP% until Aug 2000, contact subrah
			,lm-smf-ir-1oc12c(991)		-- 1 Port 622-Mbps, SMFIR-2-622/C(Intermediate Reach) Back card, SC Connector %DNP% until Aug 2000, contact subrah
			,lm-smf-lr-1oc12c(992)		-- 1 Port 622-Mbps, SMFLR-2-622/C (Long reach )Back card, SC Connector  %DNP% until Aug 2000, contact subrah
			,lm-mmf-4oc3c(993)		-- 4 Port 155-Mbps, MMF-4-155/C (Multi Mode Fiber) Back card, SC Connector %DNP% until Aug 2000, contact subrah
			,lm-smf-ir-4oc3c(994)		-- 4 Port 155-Mbps, SMFIR-4-155/C (Intermediate Reach) Back card, SC Connector %DNP% until Aug 2000, contact subrah
			,lm-smf-lr-4oc3c(995)		-- 4 Port 155-Mbps, SMFLR-4-155/C (Long reach) Back card, SC Connector %DNP% until Aug 2000, contact subrah
			,lm-mmf-8oc3b(996)		-- 8 Port, 155-Mbps, MMF-8-155MT/B (Multi Mode Fiber) Back card, MT-RJ Connector %DNP% until Aug 2000, contact subrah
			,lm-smf-ir-8oc3b(997)		-- 8 Port, 155-Mbps, SMFIR-8-155LC/B (Intermediate Reach) Back card, LC Connector %DNP% until Aug 2000, contact subrah
			,lm-smf-lr-8oc3b(998)		-- 8 Port, 155-Mbps, SMFLR-8-155LC/B (Long Reach) Back card, LC Connector %DNP% until Aug 2000, contact subrah
			,lm-smb-6t3(999)		-- This back card module is a 6 port T3 Line Module using SMB connector %DNP% until Jul 2001, contact rli
--      1000-1049:      UBR cards                       %DNP%
			,ubr-radio(1000)		-- Point to Point Wireless line card for UBR7200 chassis %DNP% until Aug 99, contact jraja
			,ubr-mc16s(1001)		-- Cable card 1 downstream 6 upstream for Spectrum management
			,ubr-mc11(1002)		-- Cable linecard 1 downstream, 1 upstream, FPGA
			,ubr-mc11c(1003)	-- Cable linecard 1 downstream, 1 upstream, ASIC C
			,ubr-mc12c(1004)	-- Cable linecard 1 downstream, 2 upstream, ASIC C
			,ubr-mc14c(1005)	-- Cable linecard 1 downstream, 4 upstream, ASIC C
			,ubr-mc16a(1006)	-- Cable linecard 1 downstream, 6 upstream, ASIC A
			,ubr-mc16b(1007)	-- Cable linecard 1 downstream, 6 upstream, ASIC B
			,ubr-mc16c(1008)	-- Cable linecard 1 downstream, 6 upstream, ASIC C
			,ubr-mc16e(1009)	-- Cable linecard 1 downstream, 6 upstream, ASIC for Europe
			,ubr-mc28c(1010)		-- Cable linecard 2 downstream, 8 upstream 
			,ubr-mc26(1011)		-- Cable linecard 2 downstream, 6 upstream
			,ubr-912c(1012)		-- Cisco uBR912-C Cable Modem Card with CSU/DSU WIC
			,ubr-912s(1013)		-- Cisco uBR912-S Cable Modem Card with Serial WIC
			,ubr-914r(1014)		-- Cisco uBR914 Cable Modem with removable WIC
			,ubr-clk(1015)		-- Cisco Cable Clock Card that provides the national clock signal to Cisco uBR7200 VXR
			,ubr-925(1016)		-- Cisco UBR925 Cable Modem/Router with VOIP and hardware accelerated IPSEC
			,ubr-mc26c(1017)	-- Cable linecard 2 downstream, 6 upstream
			,ubr-he-radio(1018)	-- Point to Multipoint wireless radio headend card with 1 downstream and 4 upstreams %DNP% until Jul 2000, contact afiguere
			,ubr-su-radio(1019)	-- Point to Multipoint wireless radio subscriber unit card  %DNP% until Jul 2000, contact afiguere
			,ubr-mc28cf(1020)	-- Cable linecard 2 downstream, 8 upstream, with F connector
			,ubr-mc28c-bnc(1021)	-- Cable linecard 2 downstream, 8 upstream, with BNC connector
			,ubr-mc26cf(1022)	-- Cable linecard 2 downstream, 6 upstream, with F connector
			,ubr-mc26c-bnc(1023)	-- Cable linecard 2 downstream, 6 upstream, with BNC connector
			,ubr-905(1024)		-- Cisco uBR905 Cable Modem with hardware accelerated IPSEC %DNP% until Oct 2000, contact jgao abudin
			,ubr-dlc24(1025)	-- DLC24 is a Digital Video Broadcasting (DVB) Linecard which supports the DVB in-band (IB) and out-of-band (OOB) standards, as well as the DAVIC OOB standard. It has 2 downstream channels, 4 upstream channels, and 1 ASI interface port
			,ubr-mc14e(1026)	-- Cable linecard, 1 downstream, 4 upstreams for Europe %DNP% until Jun 2001, contact azlina-group
			,ubr-mc11e(1027)	-- Cable linecard, 1 downstream, 1 upstreams for Europe %DNP% until Jun 2001, contact azlina-group
			,ubr-mlc(1028)		-- UBR based Media Line Card for MPEG video processing %DNP% until Dec 2001, contact  azlina-group
			,ubr-mc520s-f(1029)	-- Cable linecard, 5 downstreams, 20 upstreams, with Spectrum Management, with F connector %DNP% until Jun 2002, contact cable-snmp-dev
			,ubr-mc520s-bnc(1030)	-- Cable linecard, 5 downstreams, 20 upstreams, with Spectrum Management, with BNC connector %DNP% until Jun 2002, contact cable-snmp-dev
			,ubr-mc520s-d(1031)	-- Cable linecard, 5 downstreams, 20 upstreams, with Spectrum Manage ment, with dense connector %DNP% until Jun 2002, contact cable-snmp-dev
			,ubr-mc28j(1032)	-- Cable modem linecard, 2 downstream, 8 upstream at 5-55MHz %DNP% until Mar 2003, contact cr-mc28j
			,ubr-mc28u(1033)	-- Docsis compliant intelligent coax cable line card with 2 downstream and 8 upstream ports for ubr72xx series cable routers. %DNP% until Apr 2003, contact jgao
			,ubr-mc16u(1034)	-- Docsis compliant intelligent coax cable line card with 1 downstream and 6 upstream ports for ubr72xx series cable routers. %DNP% until Apr 2003, contact jgao
			,ubr-mc28x(1035)	-- Docsis compliant intelligent coax cable line card with 2 upstream and 8 downstream ports and integrated upstream for ubr72xx routers. %DNP% until Apr 2003, contact jgao
			,ubr-mc16x(1036)	-- Docsis compliant intelligent coax cable line card with 1 upstream and 6 downstream ports and integrated upstream converter for ubr72xx routers. %DNP% until Apr 2003, contact jgao
			,ubr-mc520ud(1037)	--  uBR10K Universal Card, 5DS w/upx, 20US, Spec An %DNP% until Jul 2003, contact cable-snmp-dev 
			,ubr-mc520uf(1038)	--  uBR10K Universal Card, 5DS w/upx, 20US, Spec An,F %DNP% until Jul 2003, contact cable-snmp-dev 

--	1050-1099:	more BFR cards			%DNP%
			,gsr-8fe-tx(1050)		-- GSR 8 port Fast Ethernet card with Copper interface 
			,gsr-8fe-fx(1051)		-- GSR 8 port Fast Ethernet card with Fiber interface 
			,ssrp-oc48-sm-sr(1052)		-- GSR 1 port SONET based SRP OC-48c/STM-16 Single Mode, Short Reach %DNP% until Sep 99, contact dzhu
			,ssrp-oc48-sm-lr(1053)		-- GSR 1 port SONET based SRP OC-48c/STM-16 Single Mode, Long Reach %DNP% until Sep 99, contact dzhu
			,pos-qoc12-sm-lr(1054)		-- GSR 4 port (Quad) OC-12 POS card, single mode, long reach
			,pos-qoc12-mm-sr(1055)		-- GSR 4 port (Quad) OC-12 POS card, multi mode, short reach
			,pos-oc48-sm-lr-sc(1056)	-- GSR 1 port Packet Over Sonet OC-48, single mode, long reach, SC connector card
			,pos-oc48-sm-sr-sc(1057)	-- GSR 1 port Packet Over Sonet OC-48, single mode, short reach, SC connector card
			,srp-oc12-sm-ir(1058)		-- GSR 1 port single mode SRP OC-12/STM-4 intermediate reach module
			,srp-oc12-sm-lr(1059)		-- GSR 1 port single mode SRP OC-12/STM-4 long reach module
			,srp-oc12-mm(1060)		-- GSR 1 port SRP OC-12/STM-4 Multimode Ring line card
			,pos-en-oc48-sr-sc(1061)	-- GSR enhanced OC-48 short reach SC connector line card
			,pos-en-oc48-sr-fc(1062)	-- GSR enhanced OC-48 short reach FC connector line card
			,pos-en-oc48-lr-sc(1063)	-- GSR enhanced OC-48 long reach SC connector line card
			,pos-en-oc48-lr-fc(1064)	-- GSR enhanced OC-48 long reach FC connector line card
			,pos-en-qoc12-sr(1065)		-- GSR enhanced 4 port OC-12 short reach line card
			,pos-en-qoc12-ir(1066)		-- GSR enhanced 4 port OC-12 intermediate reach line card 
			,copper-6ds3(1067)		-- GSR 6 port copper DS3 interface line card
			,copper-12ds3(1068)		-- GSR 12 port copper DS3 interface line card
			,pos-oc192-sm-ir-fc(1069)	-- GSR 1 port Packet Over SONET OC-48c/STM-16 Single Mode Intermediate Reach with FC connector %DNP% until Apr 2000, contact dprairie
			,pos-oc192-sm-sr-fc(1070)	-- GSR 1 port Packet Over SONET OC-48c/STM-16 Single Mode Short Reach with FC connector %DNP% until Apr 2000, contact dprairie
			,pos-oc192-sm-ir-sc(1071)	-- GSR 1 port Packet Over SONET OC-48c/STM-16 Single Mode Intermediate Reach with SC connector %DNP% until Apr 2000, contact dprairie
			,pos-oc192-sm-sr-sc(1072)	-- GSR 1 port Packet Over SONET OC-48c/STM-16 Single Mode Short Reach with SC connector %DNP% until Apr 2000, contact dprairie
			,gsr-sfc16(1073)		-- GSR Switch Fabric Card for 12016
			,gsr-csc16(1074)		-- GSR 12016 Clock Scheduler Card %DNP% dec 1999, sdurham
			,gsr-3ge(1075)			-- GSR 3 Port Gigabit Ethernet Line Card 
			,gsr-alarm16(1076)		-- GSR Alarm module
			,gsr-bus-board16(1077)		-- GSR Bus Board for Power distribution
			,srp-oc12-sm-xr(1078)		-- GSR 1 port single mode SRP OC-12/STM-4 extra long reach module	
			,pos-en-qoc12-mm(1079)		-- GSR enhanced 4 port OC-12 multimode line card 
			,pos-en-qoc48-sm-sr-fc(1080)	-- GSR enhanced 4 Port Packet Over Sonet OC-48, Single Mode, Short Reach, FC Connector Card
			,pos-en-qoc48-sm-sr-sc(1081)	-- GSR enhanced 4 Port Packet Over Sonet OC-48, Single Mode, Short Reach, SC Connector Card
			,pos-en-qoc48-sm-lr-sc(1082)	-- GSR enhanced 4 Port Packet Over Sonet OC-48, Single Mode, Long Reach, SC Connector Card
			,pos-en-qoc48-sm-lr-fc(1083)	-- GSR enhanced 4 Port Packet Over Sonet OC-48, Single Mode, Long Reach, FC Connector Card
			,gsr-6ct3(1084)			-- GSR 6 Port Channelized T3 Line Card 
			,pos-en-oc192-sm-lr-fc(1085)	-- GSR enhanced 1 Port Packet Over Sonet OC-192, Single Mode, Long Reach, FC Connector Card
			,pos-en-oc192-sm-lr-sc(1086)	-- GSR enhanced 1 Port Packet Over Sonet OC-192, Single Mode, Long Reach, SC Connector Card
			,pos-en-oc192-sm-vsr-sc(1087)	-- GSR enhanced 1 Port Packet Over Sonet OC-192, Single Mode, Very Short Reach, SC Connector Card
			,pos-en-oc192-sm-vsr-fc(1088)	-- GSR enhanced 1 Port Packet Over Sonet OC-192, Single Mode, Very Short Reach, FC Connector Card
			,pos-en-oc192-sm-sr-fc(1089)	-- GSR enhanced 1 Port Packet Over Sonet OC-192, Single Mode, Short Reach, FC Connector Card %DNP% until Jun 2000, contact mksliu
			,pos-en-oc192-sm-sr-sc(1090)	-- GSR enhanced 1 Port Packet Over Sonet OC-192, Single Mode, Short Reach, SC Connector Card %DNP% until Jun 2000, contact mksliu
			,gsr-sfc16-oc192(1091)		-- GSR 12016 OC192 Switch Fabric Card
			,gsr-csc16-oc192(1092)		-- GSR 12016 OC192 Clock Scheduler Card
			,atm-en-4p-oc12c-mm(1093) 	-- GSR enhanced 4 Port OC12c/STM-4c ATM multi-mode %DNP% until Oct 2000, contact ekleung vkoshi
			,gsr-qoc12-chstsds3-sm-ir-sc(1094)	-- GSR 4 port OC12 channelized to STS-12c/STM-4, STS-3c/STM1, or DS-3, Single Mode, Intermediate Reach and SC connector line card %DNP% until Jan 2001, contact zuobing
			,gsr-qoc12-chstsds3-mm-sr-sc(1095)	-- GSR 4 port OC12 channelized to STS-12c/STM-4, STS-3c/STM1, or DS-3, Multi Mode, Short Reach and SC connector line card %DNP% until Jan 2001, contact zuobing
			,gsr-oc48-chstsds3-mm-sr-sc(1096)	-- GSR 1 port OC48 channelized to STS-48c/STM16, STS-12c/STM-4, STS-3c/STM1 or DS-3, Multi Mode, Short Reach  and SC  connector line card  %DNP% until Jan 2001, contact zuobing
			,gsr-oc48-chstsds3-sm-ir-sc(1097)	-- GSR 1 port OC48 channelized to STS-48c/STM16, STS-12c/STM-4, STS-3c/STM1 or DS-3, Single Mode, Intermediate Reach and SC connector line card %DNP% until Jan 2001, contact zuobing
			,gsr-oc48-chstsds3-sm-lr-sc(1098)	-- GSR 1 port OC48 channelized to STS-48c/STM16, STS-12c/STM-4, STS-3c/STM1 or DS-3, Single Mode, Long Reach and SC connector line card %DNP% until Jan 2001, contact zuobing
			,gsr-16oc3-chstsds3-mm-sr-sc(1099)	--  GSR 16 port OC3 channelized to STS-3c/STM-1 or DS-3; Multi Mode fiber, Short Reach, SC connector line card %DNP% until Jan 2001, contact zuobing
--      1100-1149:      more 16xx, 26xx, & 36xx cards   %DNP%
			,aim-lc-4e1-compression(1100)	-- Lowcost 4 E-1 Compression AIM 
			,vic-2fxo-m1(1101)		-- 2 port Foreign eXchange Office Voice Interface Cards (Module 1) for North America %DNP% until Oct 99, contact cltarng
			,pm-nm-to-aim(1102)		-- Network Module to Advanced Interface Port Module for the 1600 and 3600 series %DNP% until Aug 2000, contact jminer
			,pm-ima-4t1-vpd(1103)		-- 4 port T1 IMA (Inverse Mux for ATM) port module with Voice Processing Deck %DNP% until Apr 2000, contact motto
			,pm-ima-4e1-vpd(1104)		-- 4 port E1 IMA (Inverse Mux for ATM) port module with Voice Processing Deck %DNP% until Apr 2000, contact motto
			,wic-csu-dsu-ft1(1105)		-- Wan Interface Card with 1 Fractional T1 DSU/CSU port for 2600, 3600 series
			,pm-ds3(1106)		-- ATM DS3 port module for 2600, 3600 series
			,pm-e3(1107)		-- ATM E3 port module for 2600, 3600 series
			,aim-t1-e1-atm(1108)		-- T1/E1 ATM Advanced Integration Module %DNP% until Aug 2000, contact ldumov
			,aim-t1-atm-24dsp(1109)		-- T1 ATM Advanced Integration Module plus 24 DSP %DNP% until Aug 2000, contact ldumov
			,aim-e1-atm-30dsp(1110)		-- E1 ATM Advanced Integration Module plus 30 DSP %DNP% until Aug 2000, contact ldumov
			,vic-2vp-fxs-did(1111)			-- 2 Port Voice Interface Card for 26/3600 Platforms.  Ports can function as Foreign Exchange Station (FXS)or Direct Inward Dialing (DID) Voice Ports (VP)
			,wic-serial-1t-12in1(1112)		-- WAN Interface Card card including 1 port serial interface, 12 in 1 connector type
			,vic-2st-2086-nt-te(1113)		-- Two port NT or TE Endpoint BRI S/T voice interface daughtercard
			,nm-aic64(1114)			-- The new alarm interface card (AIC) network module with 64 monitoring points on the C26xx/C3600 platform
			,mix3660-64(1115)		--  TDM Module that enables TDM switching on C3660 platform
			,wic-async-1am(1116)		--  WAN Interface Card - 1 Port Analog Modem
			,wic-async-2am(1117)		--  WAN Interface Card - Dual Analog Modem
			,aim-3dsps(1118)		--  DSP only AIM with 3 DSPs %DNP% until Jan 2001, contact tyu
			,aim-4dsps(1119)		--  DSP only AIM with 4 DSPs %DNP% until Jan 2001, contact tyu
			,hdv-4fxs(1120)			-- 4-Port FXS High Density Analog Voice Module
			,c2610m(1121)			-- c2600M with 1 integrated ethernet interface
			,c2611m(1122)			-- c2600M with 2 integrated ethernet interfaces
			,vic-2fxo-cama(1123)		-- 2 port FXO card, supports 911 calls on 36xx/26xx %DNP% until Nov 2001, contact asmoghe
			,wic-ethernet(1124)		-- WIC-1ENET card for 17xx platforms
			,nm-1ge(1125)			-- Network Module with 1 port Gigabit Ethernet (GE) interface, %DNP% until May 2002, contact nkumaran
			,nm-ima-4t1e1(1126)		-- 4 port T1/E1 IMA (Inverse Mux for ATM) Network Module %DNP% until Sep 2002, contact ldumov
			,nm-ima-8t1e1(1127)		-- 8 ort T1/E1 IMA (Inverse Mux for ATM) Network Module %DNP% until Sep 2002, contact ldumov
			,nm-16eswitch(1128)		-- 16 Ports 10BaseT/100BaseTX EtherSwitch Network module with optional GE and IP Phone Line Power %DNP% until Dec 2001, contact reeve
			,dnm-36eswitch(1129)		-- 36 port 10BaseT/100BaseTX EtherSwitch Doublewide Network Module with optional GE and IP Phone Line Power %DNP% until Dec 2001, contact reeve
			,nm-1t3e3(1130)			-- One port Clear T3/E3 Network Module
			,nm-1ct3e3(1131)		-- One port Channelized T3/E3 Network Module
			,nm-8ct1e1(1132)		-- Eight port Channelized T1/E1 Network Module
			,hda-em-4fxo(1133)              -- 4-port FXO Expansion Module for High Density Analog Voice Interface Daughtercard
			,nm-ce-bp(1141)			-- Content Engine Network Module Basic Performance %DNP% until Jul 2002, contact rmanian
			,nm-ce-hp(1142)			-- Content Engine Network Module High Performance %DNP% until Jul 2002, contact rmanian
                        ,c2610xm-1fe(1134)                  -- Card with 1 integrated fast ethernet interface with SDRAM for Cisco 2610XM platform
                        ,c2611xm-2fe(1135)                  -- Card with 2 integrated fast ethernet interfaces with SDRAM for Cisco 2611XM platform
                        ,c2620xm-1fe(1136)                  -- Card with 1 integrated fast ethernet interface with SDRAM for Cisco 2620XM platform
                        ,c2621xm-2fe(1137)                  -- Card with 2 integrated fast ethernet interfaces with SDRAM for Cisco 2621XM platform
                        ,c2650xm-1fe(1138)                  -- Card with 1 integrated fast ethernet interface with SDRAM for Cisco 2650XM platform
                        ,c2651xm-2fe(1139)                  -- Card with 2 integrated fast ethernet interfaces with SDRAM for Cisco 2651XM platform
			,nm-16as(1140)		 	-- 16 port Async/Sync Network Module provides low speed serial interface for the MAR's family of platforms %DNP% until Dec 2002, contact moshaikh 
			,nm-1fe-2w-v2(1143)		-- 1 Fast Ethernet 2 WAN version 2 %DNP% until Mar 2002, contact nipa
			,nm-1fe-1r-2w-v2(1144)		-- 1 Fast Ethernet 1 Token Ring  WAN version 2 %DNP% until Mar 2002, contact nipa
			,nm-2fe-2w-v2(1145)		-- Fast Ethernet 2 WAN version 2 %DNP% until Mar 2002, contact nipa
			,nm-1fe-smf(1146)		-- Network module with 1 port fast ethernet over Single Mode Fiber(SMF) connection %DNP% until Aug 2002, contact nkumaran
			,nm-1ct1e1-pri(1147)		-- One port Primary Rate Interface (PRI)  Channelized T1/E1 Network Module 
			,nm-2ct1e1-pri(1148)		-- Two port Primary Rate Interface (PRI)  Channelized T1/E1 Network Module 
			,nm-ceoip-4t1e1(1149)		-- Four port T1/E1 Circuit Emulation over IP network module %DNP% until Jul 2003, contact ssamant

--	1150-1179:	7100 series cards		%DNP%
			,io-2fe-tx-isl(1150)		-- I/O card Dual 10/100 Fast Ethernet ISL card for the 7100 series
			,ism-ipsec-mppe(1151)		-- Integrated Service Module, used only in slot 5 of the 7100 series, is a hardware accelerator for IPSEC Encryption and Compression, and MPPE encryption.
			,vpn-accelerator(1152)		-- VPN Encryption Accelerator Engine
			,vpn-accelerator-module2(1153)	-- VPN Encryption Accelerator Engine 2
			,vpn-accelerator-AES(1154)	-- VPN Encryption Accelerator Engine with AES Support
--	1180-1299:	yet more cpu-type cards		%DNP%
			,cre-rp(1180)			-- Central Routing Engine - Route Processor for Cisco 10000 series
			,cre-fp(1181)			-- Central Routing Engine - Forwarding Processor for Cisco 10000 series %DNP% until Mar 2000, contact bilafer
			,cpu-as5400(1182)		-- CPU card for AS5400
			,cpu-rsp8(1183)			-- RSP8 Zbus capable controller board/card for the 7500 series %DNP% until Mar 2000, contact doi "Afterburner" project
			,cpu-trp(1184)			-- Turbo Route Processor board/card for the 7500 series %DNP% until Mar 2000, contact doi "Esperanza" project
			,cpu-mc3810-v3(1185)		-- CPU card for the MC3810-V3; higher performance than MC3810 with NEBs compliant changes.
			,cpu-7200-nse1(1186)		-- CPU card for use in the 7200 series, Network Service Engine 1.  Contains a PXF (Parallel Express Forwarding) processor to accelerate layer 3-7 IP features.
			,cpu-as5850(1187)			-- CPU card for AS5850 %DNP% until Sept 2000, contact  samip
			,cpu-7200-npe400(1188)		-- Network processing engine (CPU card) for 7200 series 
			,cpu-as5350(1189)		-- CPU card for AS5350 %DNP% until Dec 2000, contact nag
			,cpu-rsp4-plus(1190)		-- RSP4+ is ECC capable RSP4, ie.  With a Tiger5 asic %DNP% until Jul 2000, contact boxiao
			,cpu-7150(1191)			-- CPU for the 7150 series
			,cpu-pxmb-45gbps(1192)		-- PXM45B Processor Module with R7K Processor %DNP% until Feb 2001, contact subrah
			,cpu-7401-nse(1193)		-- Cisco 7401 Network Processing Engine %DNP% until Feb 2001, contact taz
			,cpu-c7160-vpe700(1194)		-- VPN performance engine CPU module for C7160 routers with 2 667Mhz processors %DNP% until Nov 2001, contact ahase
			,cpu-rsp16(1195)  -- RSP8 Plus board processor %DNP% until Sep 2001, contact mssunil
			,cpu-gsr-prp1(1196)		-- GSR Performance Route Processor 1 
			,cpu-c7300-nse100(1197)		-- Network Service Engine 100 (CPU card) for Cisco 7300 platform %DNP% until Sep 2001, contact anshih
			,cpu-pxm1e-1gbps(1198)		-- Cisco MGX88XX Processor Switch Module 1 Enhancement version %DNP% until Jan 2002, contact wwcai
			,cpu-pxm1e-2oc12(1199)		-- Cisco MGX88XX Processor Switch Module 1, 2 OC12 ports, Enhanced version with PNNI support %DNP% until Jan 2002, contact wwcai
			,cpu-pxm1e-8oc3(1200)		-- Cisco MGX88XX Processor Switch Module 1 Enhancement version with PNNI support %DNP% until Jan 2002, contact wwcai
			,cpu-pxm1e-8t3e3(1201)		-- Cisco MGX88XX Processor Switch Module 1 Enhanced version with 8 T3/E3 ports %DNP% until Jan 2002, contact wwcai
			,cpu-pxm1e-combo-t3e3oc3(1202)	-- Cisco MGX88XX Processor Switch Module 1 Enhanced version combo card with 8 T3/E3 and 4 OC3 ports %DNP% until Jan 2002, contact wwcai
			,cpu-7200-npeg1(1203)		-- Network Processing Engine (CPU card) for 7200VXR series %DNP% until Nov 2001, contact mhyne
			,cpu-c2691-2fe(1204)		-- c2691 Motherboard with Fast Ethernet 
			,cpu-c3745-2fe(1205)		-- c3745 Motherboard with Fast Ethernet 
			,cpu-c3725-2fe(1206)		-- c3725 Motherboard with Fast Ethernet 
			,cpu-c3631-1fe(1207)		-- c3631 Motherboard with Fast Ethernet 
			,cpu-mwr1900-2fe(1208)		-- MWR 1900 Motherboard with Fast Ethernet %DNP% until Apr 2002, contact dblanken
			,cpu-6400-nsp(1209)             -- Cisco 6400 Node Switch Processor
                        ,cpu-6400-nrp(1210)             -- Cisco 6400 Node Route Processor
                        ,cpu-6400-nrp2(1211)            -- Cisco 6400 Node Route Processor 2
                        ,cpu-6400-nrp2-sv(1212)         -- Cisco 6400 Node Route Processor 2 with Shaped VCs
			,cpu-3200(1213)			-- Mobile Router Card for the 3200 Platform %DNP% until Mar 2002, contact srikkris
			,cpu-7301-npeg1(1214)		-- Cisco 7301 Network Processing Engine %DNP% until Jan 2003, contact dhom
			,cpu-pxm1e-16-t1e1(1215)	-- PXM1E-16-T1E1 processor card supports 16 port T1E1 IMA(Inverse Multplexing for ATM) %DNP% unitl Jul 2002, contact wwcai
			,cpu-c7300-nse100-plus(1216)	-- Network Service Engine 100+ for Cisco 7300 platform %DNP% until Jun 2002, contact anshih
			,cpu-as5400-hpx(1217)		-- CPU card for AS5400HPX
			,cpu-as5350-hpx(1218)		-- CPU card for AS5350HPX %DNP% until Jun 2002, contact vdukki
			,cpu-c7160-vpe1000(1219)	-- VPN performance engine CPU module for C7160 routers with 2 933Mhz processors %DNP% until Nov 2001, contact ahase
			,cpu-c7160-vpe1500(1220)	-- VPN performance engine CPU module for C7160 routers with 2 1.5Ghz processors %DNP% until Nov 2001, contact ahase
			,cpu-as5850-tb(1221)            -- BCM1250-based CPU card for AS5850 RSC %DNP% until June 2002, contact  vdukki
			,cpu-c7300-npeg100(1222)	-- Network Processing Engine (CPU card) for Cisco 7300 platform  %DNP% until Apr 2003, contact  anshih
			,cpu-c3220(1223)		-- Mobile Access Router Card(MARC) for 3220 Platform With 1 Fast Ethernet I/F %DNP% until May 2003, contact pnoone
			,cpu-vg224(1224)		-- Line Side Analog Gateway with 24FXS Analog ports
			,cpu-3745xm-2ge(1225)		-- c3745XM Motherboard with Gigabit Ethernet %DNP% until oct 2004, contact abhalgat
			,cpu-3725xm-2ge(1226)		-- c3725XM Motherboard with Gigabit Ethernet %DNP% until oct 2004, contact abhalgat

--	1300-1349:	10000 series cards		%DNP%
			,pos-1oc12(1300)		-- 1 port OC12 Packet over Sonet card %DNP% until Mar 2000, contact bilafer
			,p6-ct3(1301)			-- 6 port channelized T3 card %DNP% until Mar 2000, contact bilafer
			,ge(1302)			-- 1 port Gigabit Ethernet card %DNP% until Mar 2000, contact bilafer
			,atm-1oc12(1303)			-- 1 port OC12 ATM card %DNP% until Aug 2000, contact jkotelly
			,p1-coc12(1304)			-- 1 port channelized OC12 card %DNP% until Apr 2000, contact ssaxena
			,p4-chstm1(1305)		-- 4 port channelized STM-1 card %DNP% until Oct 2000, contact ssaxena
			,p1-esp(1306)			-- 1 Port Encrption Services Processor %DNP% until Mar 2001, contact leblancd
			,acc-24fe-tx(1307)		-- c10720 24 ports fast ethernet Tx access card
			,acc-24fe-fx-mm(1308)		-- c10720 24 ports fast ethernet FX MM (2km) access card
			,acc-24fe-fx-sm(1309)		-- c10720 24 ports fast ethernet FX SM (15km) access card
			,srp-oc48-sr(1310)		-- c10720 1 port OC-48c SRP SM short reach uplink card
			,srp-oc48-ir(1311)		-- c10720 1 port OC-48c SRP SM intermediate reach uplink card
			,pos-6oc3(1312)			-- 6 port OC3 Pocket over Sonet Card for the 10000 ESR %DNP% until Sep 2001, contact smaini
			,atm-4oc3(1313)			-- 4 port OC3 ATM line card with single mode, intermediate reach optics for the C10000 platform %DNP% until Sep 2001, contact derogers
			,p8-e3ds3(1314)			-- 8 port unchannalized switchable t3/e3 %DNP% until Sep 2001, contact jroumas
			,srp-pos-1oc48-sm-sr(1315)	-- 1 Port OC48 SRP or POS SM short reach card %DNP% until Oct 2001, contact gjigarji
			,srp-pos-1oc48-sm-lr(1316)	-- 1 Port OC48 SRP or POS SM long reach card %DNP% until Oct 2001, contact gjigarji
			,flashcard-48mb(1317)		-- Cisco 10000 48 MB Flash Card %DNP% until Feb 2002, contact enjimene
			,flashcard-128mb(1318)		-- Cisco 10000 128 MB Flash Card %DNP% until Feb 2002, contact enjimene
			,p24-ct1e1(1319)		-- 24 Port Channelized E1/T1 card %DNP% until Feb 2002, contact enjimene
-- %DNP% reuse this assignmet	,p-mlc-asi-cmts(1320)		
-- %DNP% reuse this assignmet	,p-mlc-asi-in(1321)
-- %DNP% reuse this assignmet	,p-mlc-asi-out(1322)
			,acc-4ge8fe-tx(1323)		-- c10720 4 port gigabit ethernet + 8 port fast ethernet access card 
			,acc-4ge8fe-fx-mm(1324)		-- c10720 4 port gigabit ethernet + 8 port fast ethernet FX MM (2km) access card 
			,acc-4ge8fe-fx-sm(1325)		-- c10720 4 port gigabit ethernet + 8 port fast ethernet FX SM (15km) access card 
			,ul-srp48-lr1(1326)		-- c10720 1 port OC-48c SRP SM Long Reach (40Km) uplink card
			,ul-srp48-lr2(1327)		-- c10720 1 port OC-48c SRP SM Long Reach (80Km) uplink card
			,pos-1oc3-oc12(1328)		-- 1 port OC3/OC12 Packet Over Sonet linecard for 10000 ESR %DNP% until Apr 2002, contact smaini
			,p8-fe(1329)			-- 8 Port Fast Ethernet line card %DNP% until Jun 2002, contact enjimene
			,c10720-mnt(1330)		-- C10720 Maintenance card
			,ge-1h(1331)			-- Half Height single port Gigabit Ethernet line card for C10000 series router %DNP% until Jul 2002, contact jwhitcom
			,ul-pos-srp48-sm-sr(1332)	-- c10720 OC-48c POS/SRP SM short reach uplink card
			,ul-pos-srp48-sm-ir(1333)	-- c10720 OC-48c POS/SRP SM intermediate reach uplink card
			,ul-pos-srp48-sm-lr1(1334)	-- c10720 OC-48c POS/SRP SM Long Reach (40Km) uplink card
			,ul-pos-srp48-sm-lr2(1335)	-- c10720 OC-48c POS/SRP SM Long Reach (80Km) uplink card
			,acc-24fe-tx-b(1336)		-- c10720 24 ports fast ethernet Tx access card revB.
			,acc-4ge8fe-tx-b(1337)		-- c10720 4 port gigabit ethernet + 8 port fast ethernet access card revB.
			,c10k-spa-jacket(1338)		-- the Shared Port Adaptor (SPA) jacket (or host) card for the c10k. It can host up to 2 SPAs.


--	1350-1449:	AS5400 cards			%DNP%
			,as5400-dfc-carrier(1350)	-- Carrier card that holds Dial Feature Cards for the AS5400 platform 
			,as5400-dfc-np348(1351)		-- Nextport (np) Modem Dial Feature Card consisting of 3 modem modules, 2 of which have 120 modems and that has 108, for a total of 348 modems per card, used in AS5400 and AS5350 platforms
			,as5400-dfc-np192(1352)		-- Nextport (np) Modem Dial Feature Card consisting of 2 modem modules, 1 of which has 120 modems the other 72, for a total of 192 modems per card, used in AS5400 and AS5350 platforms
--	1450-1500:	Common Cards			%DNP%
			,dfc-8ce1(1450)			-- 8 Primary Rate Interface (PRI) Channelized E1 (ce1) Dial Feature Card used in AS5400 and AS5800 platforms 
			,dfc-8ct1(1451)			-- 8 Primary Rate Interface (PRI) Channelized T1 (ct1) Dial Feature Card used in AS5400 and AS5800 platforms  %DNP% until Dec 99, contact rmeadows
			,dfc-ct3(1452)			-- Channelized T3 (ct3) Dial Feature Card used in AS5400 and AS5800 platforms  %DNP% until Dec 99, contact rmeadows
			,dfc-np108(1453)		-- Nextport (np) Modem Dial Feature Card consisting of 3 modem modules, each module has 36 modems, for a total of 108 modems per card, used in AS5400 and AS5800 platforms %DNP% until Dec 99, contact rmeadows
			,isa-ipsec-mppe(1454)		-- Integrated Service Port Adapter, used in the 7100 and 7200 series as a module, and in the 7500 series as a Port Adapter.  Hardware Accelerator for IPSEC Encryption and Compression, and MPPE encryption.  May not be used in slot 5 of the 7100. 
			,wic-dslsar-20150(1455)		-- DSLSAR ADSL WIC (Wan Interface Card) used in 1720, 1750, 2600 and 3600 series.  DSLSAR - SAR (Segmentation & Reassembly) of ATM cells and can be used with any DSL (Digital Subscriber Line). Uses ADSL (Asymmetric Digital Subscriber Line) as the physical layer. 
			,dfc-4ce1(1456)			-- 4 Primary Rate Interface (PRI) Channelized E1 (ce1) Dial Feature Card used in AS5350 platform %DNP% until Dec 2000, contact nag
			,dfc-4ct1(1457)			-- 4 Primary Rate Interface (PRI) Channelized T1 (ct1) Dial Feature Card used in AS5350 platform %DNP% until Dec 2000, contact nag
			,dfc-2ce1(1458)			-- 2 Primary Rate Interface (PRI) Channelized E1 (ce1) Dial Feature Card used in AS5350 platform %DNP% until Dec 2000, contact nag
			,dfc-2ct1(1459)			-- 2 Primary Rate Interface (PRI) Channelized T1 (ct1) Dial Feature Card used in AS5350 platform %DNP% until Dec 2000, contact nag
			,dfc-np60(1460)			-- Nextport (np) Dial Feature Card, supports a total of 60 universal ports per card %DNP% until Dec 2000, contact nag
			,spe-np6(1461)			-- NextPort(np) SPE(DSP), supports 6 universal ports per spe %DNP% until Oct 2000, contact ashok
			,wvic-2dsu-t1-dir(1462)		-- WAN Voice Interface Cards with a dual port T1 DSU with drop & insert and protection switching relay for MWR1900 %DNP% until Jan 2002, contact dblanken
			,wvic-2dsu-e1-dir(1463)		-- WAN Voice Interface Cards with a dual port E1 DSU with drop & insert and protection switching relay for MWR1900 %DNP% until Jan 2002, contact dblanken
			,vic-4vp-fxs-did(1464)		-- 4 port Voice Interface Card; Each port can function as Foreign Exchange Station(FXS) or Direct Inward Dialing (DID) Voice Port
			,vic-4fxo-us-m1(1465)		-- Four port Foreign Exchange Office Voice Interface Card for US/North America or M1 interface
			,vic-4fxo-m2-m3(1466)		-- Four port Foreign Exchange Office Voice Interface Card for M2 or M3 interface (software selectable on a card basis)
			,vic-4fxo-cama(1467)		-- Four port Foreign Exchange Office Voice Interface Card for US/North America with CAMA (Centralized Automated Message Accounting) 911 signalling support (software selectable per port basis)
			,wic-gshdsl-atm-t1-e1(1468)	-- A G.SHDSL WIC (WAN INterface Card) in both ATM and T1/E1 Framed Modes for the 26xx/36xx MARS Platform %DNP% until Oct 2001, contact bhagvan
			,mgx-srm-e1-oc3(1469)		-- Cisco MGX88xx Service REdundancy Module (SRM) E %DNP% until Jan 2002, contact wwcai
			,p2-coc12(1470)               -- 2 port channelized OC12 linecard %DNP% until Feb 2002, contact jedavids
			,vic-8fxo-us-m1(1471)		-- 8 Port FXO Voice Interface Module for US/North America or M1 interface %DNP% until Jul 2002, contact mananthr
			,p8-ds3-e3-atm(1472)		-- 8 Port DS3/E3 ATM Line Card %DNP% until Jun 2002, contact jcolom
			,c3201-smic(1473)		-- Serial Mobile Interface Card for the C3200 family %DNP% until Mar 2002, contact srikkris	
			,c3201-4fes-mic(1474)		-- 4 port 10/100 Fast Ethernet Switch Mobile Interface Card for c3200 Mobile IP router %DNP% unitl Nov 2002, contact lucychiu
			,wic-dslsar-20174-isdn(1475)	-- Single port ADSL Wan Interface Card to support ADSL over ISDN and dying gasp, to be used on c1700, c2600 and c3700 routers %DNP% until Aug 2002, contact jerryc
			,wic-dslsar-20174-pots(1476)	-- Single port ADSL Wan Interface Card to support ADSL over POTS and dying gasp, to be used on c1700, c2600 and c3700 routers %DNP% until Aug 2002, contact jerryc
			,nm-se(1477)			-- service engine network module
			,aim-se(1478)			-- service engine Advanced Interface Module
			,wic-se(1479)			-- service engine WIC
			,dfc-16ce1(1480)		-- 16 Primary Rate Interface (PRI) Channelized E1 (ce1) Dial Feature Card used in AS5400 and AS5800 platforms %DNP% until Apr 2003, contact vshyam 
			,dfc-16ct1(1481)		-- 16 Primary Rate Interface (PRI) Channelized T1 (ct1) Dial Feature Card used in AS5400 and AS5800 platforms %DNP% until Apr 2003, contact vshyam
			,ipsec-sw-vpa(1482)		--IP Security Single-Wide Versatile Port Adaptor (SW-VPA).  Provides hardware acceleration for IPSec encryption/decryption and IKE
			,oc3-atm2-vpa(1483)		-- 2 port OC-3c/STM-1 ATM Versitile Port Adapter (VPA)
			,oc3-atm4-vpa(1484)		-- 4 port OC-3c/STM-1 ATM Versitile Port Adapter (VPA)
			,oc12-atm1-vpa(1485)		-- 1 port OC-12c/STM-4 ATM Versitile Port Adapter (VPA)
			,oc12-atm2-vpa(1486)		-- 2 port OC-12c/STM-4 ATM Versitile Port Adapter (VPA)
			,oc48-atm1-vpa(1487)		-- 1 port OC-48c/STM-16 ATM Versitile Port Adapter (VPA)
			,t3e3-atm2-vpa(1488)		-- 2 port T3/E3 ATM Versitile Port Adapter (VPA)
			,t3e3-atm4-vpa(1489)		-- 4 port T3/E3 ATM Versitile Port Adapter (VPA)			
			,oc3-pos2-vpa(1490)		-- 2 port OC3c Versatile Packet Over Sonet Port Adapter (POS VPA) %DNP% until Jun 2003, contact  rramacha
			,oc3-pos4-vpa(1491)		-- 4 port OC3c Versatile Packet Over Sonet Port Adapter (POS VPA) %DNP% until Jun 2003, contact  rramacha
			,oc12-pos1-vpa(1492)		-- 1 port OC12c Versatile Packet Over Sonet Port Adapter (POS VPA) %DNP% until Jun 2003, contact  rramacha
			,oc12-pos2-vpa(1493)		-- 2 port OC12c Versatile Packet Over Sonet Port Adapter (POS VPA) %DNP% until Jun 2003, contact  rramacha
			,oc12-pos8-vpa(1494)		-- 8 port OC12c Versatile Packet Over Sonet Port Adapter (POS VPA) %DNP% until Jun 2003, contact  rramacha
			,fe4-vpa(1495)			-- 4 port 10/100 Ethernet Versatile Port Adapter (VPA) %DNP% until Sep 2003, contact  yega
			,ge2-vpa(1496)			-- 2 port 10/100/1000 Ethernet Versatile Port Adapter (VPA) %DNP% until Sep 2003, contact  yega
			,wic-eswitch4(1497)		-- 4 Ports 10BaseT/100BaseTX Ethernet Switch card %DNP% until Jul 2003, contact mananthr

--	1501-1549:	Catalyst 6000 Cards		%DNP%
			,cat6k-msfc(1501)		-- Multilevel Switching Feature Card for the Catalyst 6000 series %DNP% until Aug 99, contact moshen
			,cat6k-wsx-sup-12ge(1502)	-- Supervisor with 2 Gigabit Ethernet ports for the Catalyst 6000 series 
			,cat6k-wsx-6408-gbic(1503)	-- Card with 8 Gigabit Ethernet ports for the Catalyst 6000 series 
			,cat6k-wsx-6224-100fx-mt(1504)	-- Card with 24 port 100BaseFX MM (MT-RJ) for the Catalyst 6000 series
			,cat6k-wsx-6248-rj45(1505)	-- Card with 48 10/100 RJ45 Fast Ethernet ports for the Catalyst 6000 series 
			,cat6k-wsx-6248-tel(1506)	-- Card with 48 10/100 RJ21 Fast Ethernet ports for the Catalyst 6000 series 
			,cat6k-wsx-6302-msm(1507)	-- Multilayer Switch Module for the Catalyst 6000 series
			,cat6k-wsx-6024-mtrj(1509)	-- Card with 24 10/100 MTRJ Fast Ethernet ports for the Catalyst 6000 series
			,cat6k-msfc2(1510)		-- Multilevel Switching Feature Card Version 2 for the Catalyst 6000 series
			,cat6k-wsx-6316-ge-tx(1511)		-- 16-port RJ-45 Gigabit ethernet module
			,cat6k-wsx-6416-gbic(1512)		-- 16-port GBIC Gigabit ethernet module
			,cat6k-wsx-6324-100fx(1513)		-- 24-port 100FX multimode MT-RJ with 128K per-port packet buffer
			,cat6k-wsx-6348-rj45(1514)		-- 48-port 10/100 ethernet module
			,cat6k-wsx-6502-10ge(1515)		-- 10 Gigabit Ethernet Base Module
			,cat6k-wsx-6066-slb-apc(1516)		-- Venus: Server Load Balancing Application Processor Complex
			,cat6k-wsx-6448-rj45(1517)		-- 48 port 10/100 Hydra2/Hydra2V %DNP% until Jan 2001, contact skilaru
			,cat6k-wsx-6548-rj45(1518)		-- 48 port 10/100 Hydra2+/Hydra2V+
			,cat6k-wsx-6248a-tel(1519)		-- Card for C6K with 48 10/100 RJ21 ports with enhanched QoS a.k.a Indus w/ Enhanced QoS
			,cat6k-wsx-sup2-2ge(1520)		-- Supervisor 2 with 2 Gigabit Ethernet ports
			,cat6k-wsc-6500-sfm(1521)		-- Catalyst 6500 Switch Fabric Module
			,cat6k-wsc-6500-sfm2(1522)		--Catalyst 6500 Switch Fabric Module II
			,cat6k-wsx-6816-gbic(1523)		-- Catalyst 6500 16 port 1000BaseX (Layer 3)
			,cat6k-wsx-24fxs(1524)		-- Catalyst 6000 24 ports FXS Station Interface Module %DNP% until Feb 2002, contact ssarkar
			,cat6k-wsx-6600-6t1(1525)	-- Catalyst 6000 6 ports T1 Interface Module %DNP% until Feb 2002, contact ssarkar
			,cat6k-wsx-6600-6e1(1526)	-- Catalyst 6000 6 ports E1 Interface Module %DNP% until Feb 2002, contact ssarkar
			,cat6k-wsx-256a(1527)		-- Catalyst 6000 256-Audio Services Module %DNP% until Feb 2002, contact ssarkar
			,cat6k-wsx-6348-rj21(1528)	-- Catalyst 6500 48 port 10/100BaseTX (RJ-21)
			,cat6k-wsx-6516-gbic(1529)	-- Catalyst 6500 16 port 1000BaseX GBIC
			,cat6k-wsx-sup1a-2ge(1530)	-- Catalyst 6500 2 port 1000BaseX Supervisor module (GBIC)
			,cat6k-wsx-6548-rj21(1531)	-- Catalyst 6500 48 port 10/100BaseTX (RJ-21)
			,cat6k-wsx-6416-gemt(1532)	-- Catalyst 6500 16 port 1000BaseSX (MT-RJ)
			,cat6k-wsx-6380-nam(1533)	-- Catalyst 6500 Network Analysis Module
			,cat6k-wsx-6248a-rj45(1534)	-- Catalyst 6500 48 port 10/100BaseTX (RJ-45)
			,cat6k-wsx-6408a-gbic(1535)	-- Catalyst 6500 8 port 1000BaseX (GBIC), Enhanced QoS module
			,cat6k-wsx-6381-ids(1536)	-- Catalyst 6500 Intrusion Detection module
			,cat6k-wsx-6524-mmmt(1537)	-- Catalyst 6500 24 port 100BaseX MM (MT-RJ) module
			,cat6k-wsx-6516-getx(1538)	-- Catalyst 6500 16 port 10/100/1000BaseT (RJ-45) module 
			,cat6k-wsx-6501-10gex4(1539)	-- Catalyst 6500 1 port 10 Gigabit Ethernet (EX4) module
			,cat6k-wsx-6816-oc3-mm(1540)	-- Catalyst 6500 16 port OC3c Packet Over Sonet Multimode %DNP% until Dec 2001, contact huifu rasim
			,cat6k-wsf-6kvpwr(1541)		-- Catalyst 6500 inline power card 
                        ,cat6k-ws-svc-nam1(1542)        -- Catalyst 6500 Network Analysis Module
                        ,cat6k-ws-svc-nam2(1543)        -- Catalyst 6500 Network Analysis Module
                        ,cat6k-ws-svc-fwm1(1544)        -- Catalyst 6500 Firewall Module
                        ,cat6k-ws-svc-ssl1(1545)        -- Catalyst 6500 SSL Module
                        ,cat6k-wsx-6516a-gbic(1546)     -- Catalyst 6500 16 port 1000BaseX (GBIC) %DNP% until May 2003, contact tjw, fxu
                        ,cat6k-ws-svc-ssl2(1548)        -- Catalyst 6500 SSL Module %DNP% until Dec 2004, contact tjw, fxu
			,ipsec-vpnsm(1549)		-- Gigabit IPsec VPN Service Module for the Catalyst 6500 and 7600
--	1550-1599:	Daughter Cards 			%DNP%
			,mdc-cat9000-earl3(1550)	--%DNP% until Jan 2000, contact cls
			,mdc-cat9000-pdlbip(1551)	--%DNP% until Jan 2000, contact cls
			,mdc-cat9000-pbd-skyway(1552)	--%DNP% until Jan 2000, contact cls
			,dslam-ni2-controller(1553)	-- Cisco 6100, 6130, 6260 DSLAM chassis NI-2 IOS controller Daughter Card %DNP% until Aug 99, contact pgili
			,wvic-2dsu-e1-di-g703(1554)	-- Two port E1 voice interface daughtercard with Drop and Insert and G.703 for 2600 series and 3600 series routers %DNP% until Jan 2000, contact murdockk
			,wvic-1dsu-e1-g703(1555)	-- One port E1 voice interface daughtercard with G.703 for 2600 series and 3600 series routers %DNP% until Jan 2000, contact murdockk
			,dspm-pvdm3(1556)		-- Packet Voice DSP module with 3 C549 DSP's used by 17x0, 26x0, and 36x0 platforms
			,encryption-des(1557)		-- DES (Data  Encryption Standard) Encryption Module that goes into the expansion slot in the 1720, 1750, and other possible platforms tbd. %DNP% until April 2000, contact lrivas project intercooler
			,encryption-3des(1558)		-- Triple DES (Data  Encryption Standard) Encryption Module that goes into the expansion slot in the 1720, 1750, and other possible platforms tbd. %DNP% until April 2000, contact lrivas project intercooler
			,dslam-ni2-controller-itemp(1559)	-- Cisco 6015, 6100, 6130, 6160, 6260 DSLAM chassis ITEMP NI-2 IOS controller Daughter Card %DNP% until May 2000, contact pej
			,vip-sa-ahdlc(1560)		-- Asynchronous HDLC service adaptor that goes in a VIP card on 7200 and 7500 platforms %DNP% until Oct 2000, contact cpechard
			,dspm-pvdm1(1561)		-- Packet Voice DSP module with 1 C549 DSP used by 17x0, 26x0, and 36x0 platforms
			,dspm-pvdm2(1562)		-- Packet Voice DSP module with 2 C549 DSPs used by 17x0, 26x0, and 36x0 platforms
			,dspm-pvdm4(1563)		-- Packet Voice DSP module with 4 C549 DSPs used by 17x0, 26x0, and 36x0 platforms
			,dspm-pvdm5(1564)		-- Packet Voice DSP module with 5 C549 DSPs used by 17x0, 26x0, and 36x0 platforms
			,hda-em-4dsp(1590)		-- 4-C5421 DSP Daughtercard
			,hda-em-10fxs(1591)		-- 10-port FXS Voice Interface Daughtercard
			,wic-sh-dsl(1565)		-- A WIC (Wan Interface Card) providing Symmetrical HIgh bit rate Digital Subscriber line (SHDSL) for 2600, 3620, 3640 and 3660 platforms %DNP% until May 2001, contact nkumaran
			,hdv-8fxs(1566)			-- 8-Port FXS Voice Interface Daughtercard
			,hdv-4dsp(1567)			-- 4-chip DSP Daughtercard
			,c7300-nse100-db(1568)		-- Network Service Engine 100 Daughtercard for Cisco 7300 platform %DNP% until Sep 2001, contact anshih
			,dying-gasp(1569)		-- Dying Gasp (Power Status Indication) Daughter Card for the G.SHDSL ATM/T1/E1 WIC for the midrange 26xx/36xx routers %DNP% until Jan 2002, contact bhagvan
			,ge-eswitch(1570)		-- Gigabit (1000BaseT) module for EtherSwitch NM and DNM %DNP% until Dec 2001, contact reeve
			,pwr-16eswitch(1571) 	        -- Power module for 16 port EtherSwitch NM TBD %DNP% until Dec 2001, contact reeve
			,pwr-36eswitch(1572)    	-- Power module for 36 port EtherSwitch DNM TBD %DNP% until Dec 2001, contact reeve
			,vic-4vp-fxs-4did(1573)	-- 4-port Direct Inward Dialing (DID) and 4-port Foreign Exchange Station (FXS) Voice Interface Daughtercard
			,c7300-nse100-plus-db(1574)	-- Network Service Engine 100+ Daughtercard for Cisco 7300 platform %DNP% until Jun 2002, contact anshih
			,vwic2-mft1-t1e1(1575)		-- VWIC2-1MFT-T1E1 (1 Port) RJ-48 Multi-Flex Trunk -T1/E1 %DNP% until May 2003, contact  hdbui
			,vwic2-mft1-g703(1576)		-- VWIC2-1MFT-G703 (1 Port) RJ-48 Multi-Flex Trunk - G.703 %DNP% until May 2003, contact  hdbui
			,vwic2-mft2-t1e1(1577)		--  VWIC2-2MFT-T1E1 (2 Port) RJ-48 Multi-Flex Trunk - T1/E1  %DNP% until May 2003, contact  hdbui
			,vwic2-mft2-g703(1578)		--  VWIC2-2MFT-G703 (2 Port)) RJ-48 Multi-Flex Trunk - G.703  %DNP% until May 2003, contact  hdbui
			,ec-mft32(1579)			-- EC-MFT-32 - 32-Channel Echo Canceller Module for Multiflex Trunk %DNP% until May 2003, contact  hdbui
			,ec-mft64(1580)			-- EC-MFT-64 - 64-Channel Echo Canceller Module for Multiflex Trunk %DNP% until May 2003, contact  hdbui
			,em-4fxs-4fxo(1581)		-- 8-port voice/fax expansion module - 4FXS/4FXO
			,em-6fxo(1582)			-- 6-port voice/fax expansion module - FXO
			,em-4bri-nt-te(1583)		-- 4-port voice/fax expansion module - BRI
			,pvdm2-dsp-half(1584)		-- Packet Voice C5510 DSP Module II with half channel capacity of C5510 DSP. %DNP% contact dobro-snmp
			,pvdm2-dsp4(1585)		-- Packet Voice C5510 DSP Module II with Four DSP in it %DNP% until Jul 2003, contact dobro-snmp
			,pvdm2-dsp3(1586)		-- Packet Voice C5510 DSP Module II with three DSP in it %DNP%  until Jul 2003,contact dobro-snmp
			,pvdm2-dsp2(1587)		-- Packet Voice C5510 DSP Module II with two DSP in it %DNP%  until Jul 2003, contact dobro-snmp
			,pvdm2-dsp1(1588)		-- Packet Voice C5510 DSP Module II with one DSP in it %DNP%  until Jul 2003, contact dobro-snmp
			,pvdm2-hwecan2(1589)		-- Packet Voice C5510 DSP Module II Supports Hardware Echo cancel with 64 channels at 64 milli seconds tail-length %DNP%  until Jul 2003, contact dobro-snmp
			,pvdm2-hwecan1(1592)		-- Packet Voice C5510 DSP Module II Supports Hardware Echo cancel with 32 channels at 64 milli seconds tail-length %DNP%  until Jul 2003, contact dobro-snmp
			,pvdm2-hwecan3(1593)		-- Packet Voice C5510 DSP Module II Supports Hardware Echo cancel with 128 channels at 64 milli seconds tail-length %DNP%  until Jul 2003, contact dobro-snmp

--	1600-1649:	Dslam Cards			%DNP%
			,ni2-wan-oc3mm-sub-oc3mm(1600)	-- Network Interface module (OC-3-MM WAN, OC-3-MM Subtend) %DNP% until Aug 99, contact pgili
			,ni2-wan-ds3-sub-2ds3(1601)	-- Network Interface module (DS-3 WAN, 2 DS-3 Subtend) %DNP% until Aug 99, contact pgili
			,atuc-1p2-cap(1602)		-- ATU-C dual-line CAP module %DNP% until Oct 99, contact pgili
			,atuc-1p2-dmt(1603)		-- ATU-C dual-line DMT module %DNP% until Oct 99, contact pgili
			,atuc-1p4-dmt(1604)		-- ATU-C quad-line DMT module %DNP% until Aug 99, contact pgili
			,lim(1605)			-- Line Interface Module %DNP% until Aug 99, contact pgili
			,ni2-wan-oc3sm-sub-oc3sm(1606)	-- Network Interface module (OC-3-SM WAN, OC-3-SM Subtend) %DNP% until Aug 99, contact pgili
			,ni2-wan-e3-sub2-e3(1607)	-- Network Interface module (E-3 WAN, 2 E-3 Subtend) %DNP% until Aug 99, contact pgili
			,ni2-wan-ds3-sub8-ds1-ima(1608)	-- Network Interface module (DS-3 WAN, 8 DS-1 IMA Subtend) %DNP% until Aug 99, contact pgili
			,atuc-1p4-cap(1609)		-- ATU-C quad-line CAP module %DNP% until Oct 99, contact pgili
			,stuc-1p4(1610)			-- STU-C quad-line module %DNP% until Sep 99, contact pgili
			,ituc-1p8(1611)			-- ITU-C octal-line module %DNP% until Mar 2000, contact tjk
			,atuc-1p4-flexi-dmt(1612)	-- Flexi DSL line card configured as DMT %DNP% until May 2000, contact maniscar
			,atuc-1p4-flexi-cap(1613)	-- Flexi DSL line card configured as CAP %DNP% until May 2000, contact maniscar
			,atuc-1p4-flexi(1614)		-- Generic Flexi DSL line card %DNP% until May 2000, contact maniscar
			,atuc-1p4-dmt-isdn(1615)	-- DMT over ISDN 4 port line card %DNP% until May 2000, contact maniscar
			,ni2-wan-oc3sm-sub-2ds3(1616)	-- Network Interface module (OC-3-SM WAN, 2 DS-3 Subtend) %DNP% until May 2000, contact maniscar
			,ni2-wan-oc3mm-sub-2ds3(1617)	-- Network Interface module (OC-3-MM WAN, 2 DS-3 Subtend) %DNP% until May 2000, contact maniscar
			,atuc-1p8-dmt(1618)		-- ATU-C octal-line DMT module %DNP% until May 2000, contact aspooner
			,stuc-1p8(1619)			-- STU-C octal-line module %DNP% until May 2000, contact aspooner
			,atuc-1p8-dmt-itemp(1620)	-- ATU-C octal-line DMT module industrial temperature grade
			,stuc-1p8-itemp(1621)		-- STU-C octal-line shdsl module industrial temperature grade
			,ni2-wan-ds3-sub8-ds1-ima-itemp(1622)	-- Network Interface module (DS-3 WAN, 8 T1/E1 IMA Subtend, Itemp) %DNP% until Aug 2000, contact pej
			,io6015-ds3-t1(1623)		-- 6015 Network I/O module (DS3, 8 T1) %DNP% until Aug 2000, contact pej
			,io6015-ds3-t1-itemp(1624)	-- 6015 Network I/O module (DS3, 8 T1, Itemp) %DNP% until Aug 2000, contact pej
			,io6015-e1(1625)		-- 6015 Network I/O module (8 E1) %DNP% until Aug 2000, contact pej
			,io6015-e1-itemp(1626)		-- 6015 Network I/O module (8 E1, Itemp) %DNP% until Aug 2000, contact pej
			,io6160-ds3-t1(1627)		-- 6160 Network I/O module (DS3, 8 T1) %DNP% until Aug 2000, contact pej
			,io6260-e1(1628)		-- 6260 Network I/O module (8 E1) %DNP% until Aug 2000, contact pej
			,io6260-e3(1629)		-- 6260 Network I/O module (3 E3) %DNP% until Aug 2000, contact pej
			,ptuc-8-pots(1630)		-- PTU-C 8-line POTS module %DNP% until Jan 2001, contact bberry
			,ptuc-16-pots(1631)		-- PTU-C 16-line POTS module %DNP% until Jan 2001, contact bberry
			,trg(1632)			-- Test and Ring Generator module %DNP% until Jan 2001, contact bberry
			,atuc-1p4-dmt-isdn-dir-conn(1633)	-- DMT over ISDN Direct Connect 4 port line card %DNP% until Sep 2000, contact leblancd
			,ni2-wan-ds3-sub-2ds3-rev2(1634)	-- Network Interface module (DS-3 WAN, DS-3 Subtend) Revision 2 %DNP% until Mar 2001, contact jharrod
			,ni2-wan-oc3sm-sub-oc3sm-rev2(1635)	-- Network Interface module (OC-3-SM WAN, OC-3-SM Subtend) Revision 2 %DNP% until Apr 2001, contact jharrod
			,ni2-wan-oc3mm-sub-oc3mm-rev2(1636)	-- Network Interface module (OC-3-MM WAN, OC-3-MM Subtend) Revision 2 %DNP% until Apr 2001, contact jharrod
			,ni2-wan-oc3sm-sub-2ds3-rev2(1637)	-- Network Interface module (OC-3-SM WAN, 2 DS-3 Subtend) Revision 2 %DNP% until Jun 2001, contact jharrod
			,ni2-wan-oc3mm-sub-2ds3-rev2(1638)	-- Network Interface module (OC-3-MM WAN, 2 DS-3 Subtend) Revision 2  %DNP% until Jun 2001, contact jharrod
			,ni2-wan-oc3sm-sub-oc3sm-itemp(1639)	-- Network Interface module (OC-3-SM WAN, OC-3-SM Subtend, Itemp) %DNP% until Apr 2001, contact jharrod
			,atuc-1p8-dmt-isdn(1640)		-- ATU-C octal-line DMT module over ISDN %DNP% until Aug 2001, contact dhom
--	1650-1699:	ICS7000 series Cards	%DNP%
			,ics7750-spe200(1650)	-- Cisco ICS 7750 System Processing Engine 200 %DNP% until May 2000, contact kconry
			,ics7750-mrp200(1651)	-- Cisco ICS 7750 Multiservice Route Processor 200 %DNP% until May 2000, contact kconry
			,ics7750-sap(1652)		-- Cisco ICS 7750 System Alarm Processor %DNP% until May 2000, contact kconry
			,ics7750-mrp300(1653)	-- Cisco ICS 7750 Multiservice Route Processor 300 %DNP% until Dec 2001, contact sundarbs
--	1700-1749:	CVA Cards	%DNP%
			,cva122(1700)		--  Cisco CVA122 Cable Voice Adapter (Residential Cable Modem with two Voice Ports)
			,cva124(1701)		--  Cisco CVA124 Cable Voice Adapter (Residential Cable Modem with four Voice Ports)
			,cva122e(1702)		--  Cisco CVA122 Cable Voice Adapter (Residential Cable Modem with two voice ports) - European version
			,cva124e(1703)		--  Cisco CVA124 Cable Voice Adapter (Residential Cable Modem with four voice ports) - European version
--	1750-1799:	Marvel (AS5850) Cards	%DNP%
			,as5850-epm-2ge(1750)	-- Route Switch Controller Card with 2 port Gigabit Ethernet %DNP% until Sept 2000, contact  samip
			,as5850-ct3-216up(1751)	-- Feature Card with Channelized T3 and 216 Universal Ports %DNP% until Sept 2000, contact  samip
			,as5850-8ce1-216up(1752)	-- Feature Card with 8 port Channelized E1 card and 216 Universal Ports %DNP% until Sept 2000, contact  samip
			,as58xx-324up(1753)	-- Feature Card with 324 Universal Ports %DNP% until Sept 2000, contact  samip
			,as5850-24e1(1754)      -- Feature Card with 24 port Channelized E1 for the AS5850 platform %DNP% until April 2001, contact samip
			,as5850-24t1(1755)      -- Feature Card with 24 port Channelized T1 for the AS5850 platform %DNP% until Aug 2001, contact samip
			,as5850-stm1(1756)	-- Feature card with STM1 for the AS5850 platform %DNP% until Jul 2002, contact padma
--	1800-1849:	AS5350 Cards		%DNP%
			,as5350-dfc-carrier(1800) 	-- Carrier card that holds Dial Feature Cards for the AS5350 platform %DNP% until Dec 2000, contact nag
--	1850-1899:	Catalyst 4000 Cards		%DNP% 
			,cat4k-gateway(1850)		-- Catalyst 4000 Access Gateway line card supporting voice and WAN (Wide Area Network) interfaces as well as conferencing and transcoding services for operation with the Cisco Call Manager %DNP% until Aug 2000, contact wfried
--	1900-1949:	more BFR Cards			%DNP%
			,gsr-16oc3-chstsds3-sm-ir-sc(1900)	--  GSR 16 port OC3 channelized to STS-3c/STM-1 or DS-3; Single Mode fiber, Intermediate Reach, SC connector line card %DNP% until Jan 2001, contact zuobing
			,gsr-16oc3-chstsds3-sm-lr-sc(1901)	--  GSR 16 port OC3 channelized to STS-3c/STM-1 or DS-3; Single Mode fiber, Long Reach, SC connector line card %DNP% until Jan 2001, contact zuobing
			,dfc-np144(1902)	-- NextPort (np) Dial Feature Card that supports 144 ports %DNP% until Jan 2001, contact bbader
			,dfc-np240(1903)	-- NextPort (np) Dial Feature Card that supports 240 ports %DNP% until Jan 2001, contact bbader
			,dfc-np480(1904)	-- NextPort (np) Dial Feature Card that supports 480 ports %DNP% until Jan 2001, contact bbader
			,gsr-2oc3-chds1(1905)	-- GSR platform card, 2 ports of OC3 (Sonet/SDH); each port is channelized to DS1 level
			,ssrp-oc192-sm-lr(1906)	-- GSR 1 port SONET based SRP OC-192c/STM-64 single mode long reach line card %DNP% until Oct 2000, contact dzhu
			,ssrp-oc192-sm-ir(1907)	-- GSR 1 port SONET based SRP OC-192c/STM-64 single mode intermediate reach line card %DNP% until Oct 2000, contact dzhu
			,ssrp-oc192-sm-sr(1908)	-- GSR 1 port SONET based SRP OC-192c/STM-64 single mode short reach line card %DNP% until Oct 2000, contact dzhu
			,ssrp-oc192-sm-vsr(1909)	-- GSR 1 port SONET based SRP OC-192c/STM-64 single mode very short reach line card %DNP% until Oct 2000, contact dzhu
			,gsr-2oc12chds3-mm(1910)	-- 2xOC12 channelized to DS3 multimode %DNP% until Aug 2000, contact dprairie
			,gsr-2oc12chds3-sm(1911)	-- OC12 channelised to DS3 singlemode %DNP% until Aug 2000, contact dprairie
			,gsr-sfc10(1912)		-- GSR Switch Fabric Card for 12010
			,gsr-csc10(1913)		-- Clock Scheduler Card for GSR 12010
			,gsr-alarm10(1914)		-- GSR Alarm module
			,gsr-bus-board10(1915)		-- GSR Bus Board for Power distribution
			,gsr-oc48-chstsds3-sm-sr-sc(1916)	-- GSR 1-port-OC48, channelized to to STS-48c/STM-16, STS-12c/STM-4, STS-3c/STM-1 or DS3, single mode, short-reach, SC connector %DNP% until Jan 2001, contact zuobing
			,gsr-e48-pos-oc48-sm-sr-sc(1917)	-- GSR, Edge Engine 48, (concatenated) 1 port OC48 POS, single mode, short-reach, SC connector %DNP% until Jan 2001, contact zuobing
			,gsr-e48-pos-oc48-sm-lr-sc(1918)	-- GSR, Edge Engine 48, (concatenated) 1 port OC48 POS, single mode, short-reach, SC connector %DNP% until Jan 2001, contact zuobing
			,gsr-e48-pos-qoc12-sm-ir-sc(1919)	-- GSR, Edge Engine 48, 4 port (concatenated) OC12 POS, single mode, intermediate reach, SC connector %DNP% until Jan 2001, contact zuobing
			,gsr-e48-pos-16oc3-sm-ir-sc(1920)	-- GSR, Edge Engine 48, 16 port (concatenated) OC3 POS, single mode, intermediate reach, SC connector %DNP% until Jan 2001, contact zuobing  
			,copper-6e3(1921)		-- GSR 6 port copper E3 interface line card
			,copper-12e3(1922)		-- GSR 12 port copper E3 interface line card
			,gsr-10pge(1923)		-- Ten port Gigabit Ethernet card for the Cisco 12000 series routers
			,gsr-1p10ge-5pge(1924)		-- One port 10Gigabit Ethernet and Five port Gigabit Ethernet card for the 12000 series routers 
			,gsr-32fe-tx(1925)		-- GSR 32 port Fast Ethernet with copper interface %DNP% until Apr 2001, contact atulk
			,gsr-e48-pos-16oc3-sm-ir-lc(1926)       -- GSR, Edge Engine 48, 16 port (concatenated) OC3 POS, single mode, intermediate reach, LC connector %DNP% until Mar 2001, contact zuobing
			,gsr-16oc3-chstsds3-sm-ir-lc(1927)      -- GSR 16 port OC3 channelized to STS-3c/STM-1 or DS-3; single mode fiber, intermediate reach, LC connector %DNP% until Mar 2001, contact zuobing
			,gsr-oc12-chds1-sm-ir-sc(1928)		-- GSR 1 port OC12 channelized to DS1, single-mode intermediate reach line card with SC connector %DNP% until Jun 2001, contact donwang
			,gsr-sfc6(1929)			-- GSR 12406 Switch Fabric Card
			,gsr-csc6(1930)			-- GSR 12406 Clock Scheduler Card
			,gsr-alarm6(1931)		-- GSR 12406 Alarm Module
			,pos-en-qoc48-vsr(1932)		-- GSR enhanced 4 Port Packet Over Sonet OC-48, Very Short Reach Card
			,pos-en-qoc48-mm-sr-sc(1933)	-- GSR enhanced 4 Port Packet Over Sonet OC-48, Multi Mode, Short Reach, SC Connector Card
			,pos-en-qoc48-sm-ir-sc(1934)	-- GSR enhanced 4 Port Packet Over Sonet OC-48, Single Mode, Intermediate Reach, SC Connector Card
			,pos-en-qoc48-sm-ir-fc(1935)	-- GSR enhanced 4 Port Packet Over Sonet OC-48, Single Mode, Intermediate Reach, FC Connector Card
			,pos-en-qoc48-sm-vlr-sc(1936)	-- GSR enhanced 4 Port Packet Over Sonet OC-48, Single Mode, Very Long Reach, SC Connector Card
			,pos-en-qoc48-sm-vlr-fc(1937)	-- GSR enhanced 4 Port Packet Over Sonet OC-48, Single Mode, Very Long Reach, FC Connector Card
			,pos-en-qoc48-sm-elr-sc(1938)	-- GSR enhanced 4 Port Packet Over Sonet OC-48, Single Mode, Extremely Long Reach, SC Connector Card
			,pos-en-qoc48-sm-elr-fc(1939)	-- GSR enhanced 4 Port Packet Over Sonet OC-48, Single Mode, Extremely Long Reach, FC Connector Card
			,pos-en-oc192-vsr(1940)		-- GSR enhanced 1 Port Packet Over Sonet OC-192, Very Short Reach Card
			,pos-en-oc192-sm-sr2-sc(1941)	-- GSR enhanced 1 Port Packet Over Sonet OC-192, Single Mode, Short Reach 2, SC Connector Card
			,pos-en-oc192-sm-sr2-fc(1942)	-- GSR enhanced 1 Port Packet Over Sonet OC-192, Single Mode, Short Reach 2, FC Connector Card
			,pos-en-oc192-sm-vlr-sc(1943)	-- GSR enhanced 1 Port Packet Over Sonet OC-192, Single Mode, Very Long Reach, SC Connector Card
			,pos-en-oc192-sm-vlr-fc(1944)	-- GSR enhanced 1 Port Packet Over Sonet OC-192, Single Mode, Very Long Reach, FC Connector Card
			,pos-en-oc192-sm-elr-sc(1945)	-- GSR enhanced 1 Port Packet Over Sonet OC-192, Single Mode, Extremely Long Reach, SC Connector Card
			,pos-en-oc192-sm-elr-fc(1946)	-- GSR enhanced 1 Port Packet Over Sonet OC-192, Single Mode, Extremely Long Reach, FC Connector Card
			,gsr-sfc12410(1947)		-- GSR 12410 Switch Fabric Card
			,gsr-csc12410(1948)		-- GSR 12410 Clock Scheduler Card
			,gsr-en-8oc3(1949)		-- GSR enhanced 8 port OC3c/STM-1 ATM LC %DNP% until Oct 2001, contact ekleung
--	1950-1999:	24xx Cards			%DNP%
			,iad2420-vm-8fxs(1950)			-- This card provides 8 analog Foreign eXchange Stations (FXS) in the Integrated Access Device 2420 (IAD2420) chassis
			,iad2420-16fxs(1951)			-- This card provides 16 analog Foreign eXchange Stations (FXS) in the Integrated Access Device 2420 (IAD2420) chassis
			,iad2420-vm-pwr(1952)			-- This card provides power supply to high density analog FXS voice module in the Integrated Access Device 2420 (IAD2420) chassis
			,iad2420-adsl(1953)			-- This card provides access to ADSL (Asymmetrical Digital Subscriber Line) over ATM (Asynchronous Transfer Mode) AAL2 (ATM Adaptation Layer 2), AAL5 (ATM Adaptation Layer 5) and various class of QoS (Quality of Service) for both voice and data service on the Integrated Access Device 2420 (IAD2420) chassis
			,iad2420-hcm1(1954)			-- High performance compression module for the IAD2420 platform equipped with one TI 549 DSP
			,iad2420-hcm2(1955)			-- High performance compression module for the IAD2420 platform equipped with two TI 549 DSPs
			,iad2420-hcm3(1956)			-- High performance compression module for the IAD2420 platform equipped with three TI 549 DSPs
			,iad2420-hcm4(1957)			-- High performance compression module for the IAD2420 platform equipped with four TI 549 DSPs
			,iad2420-hcm5(1958)			-- High performance compression module for the IAD2420 platform equipped with five TI 549 DSPs
			,iad2420-hcm6(1959)			-- High performance compression module for the IAD2420 platform equipped with six TI 549 DSPs
			,iad2420-cpu(1960)			-- CPU card for IAD2420
			,iad2420-mfm-e1-unbalanced(1961)	-- IAD2420 E1 75 ohms unbalanced
			,iad2420-mfm-e1-dsx1-csu(1962)		-- IAD2420 E1 100/120 ohms balanced
			,iad2420-mfm-t1-dsx1-csu(1963)		-- IAD2420 T1 100/120 ohms balanced only
			,iad2420-8fxo(1964)			--  High density 8 analog Foreign eXchange Office (FXO) module
			,iad2420-hdsl2(1965)                    -- Symmetric DSL Module providing High-bit rate Digital Subscriber Line type 2 for IAD2420 %DNP% until Jul 2001, contact ypatel
			,iad2420-gshdsl-sdsl(1966)              -- Symmetric DSL Module providing Symmetric High-bit rate Digital Subscriber Line for IAD2420 %DNP% until Jul 2001, contact ypatel
			,iad2420-16fxs-off-premise(1967)	-- IAD2420 Sixteen FXS Off Premise Analog Voice Module 
			,gsr-atm-en-8oc3-mm(1968)		-- GSR enhanced 8 port OC3c/STM-1 Multimode ATM LC
			,gsr-oc48-msr(1969)			-- Cisco 12000 Series 2.5G Modular Services Card %DNP% until Apr 2003 contact sylvieb
			,pos-e-2oc192-vsr(1970)			-- GSR Edge 2 Port Packet Over Sonet OC-192, Very Short Reach Card %DNP% until Jan 2004, contact srinud
			,pos-e-2oc192-sm-sr2-sc(1971)		-- GSR Edge 2 Port Packet Over Sonet OC-192, Single Mode, Short Reach 2, SC Connector Card %DNP% until Jan 2004, contact srinud
			,pos-e-2oc192-sm-sr2-fc(1972)		-- GSR Edge 2 Port Packet Over Sonet OC-192, Single Mode, Short Reach 2, FC Connector Card  %DNP% until Jan 2004, contact srinud
			,pos-e-2oc192-sm-sr-sc(1973)		-- GSR Edge 2 Port Packet Over Sonet OC-192, Single Mode, Short Reach, SC Connector Card %DNP% until Jan 2004, contact srinud
			,pos-e-2oc192-sm-sr-fc(1974)		-- GSR Edge 2 Port Packet Over Sonet OC-192, Single Mode, Short Reach, FC Connector Card %DNP% until Jan 2004, contact srinud
			,pos-e-2oc192-sm-ir-sc(1975)		-- GSR Edge 2 Port Packet Over Sonet OC-192, Single Mode, Intermediate Reach, SC Connector Card %DNP% until Jan 2004, contact srinud
			,pos-e-2oc192-sm-ir-fc(1976)		-- GSR Edge 2 Port Packet Over Sonet OC-192, Single Mode, Intermediate Reach, FC Connector Card %DNP% until Jan 2004, contact srinud
			,pos-e-2oc192-sm-lr-sc(1977)		-- GSR Edge 2 Port Packet Over Sonet OC-192, Single Mode, Long Reach, SC Connector Card %DNP% until Jan 2004, contact srinud
			,pos-e-2oc192-sm-lr-fc(1978)		-- GSR Edge 2 Port Packet Over Sonet OC-192, Single Mode, Long Reach, FC Connector Card %DNP% until Jan 2004, contact srinud
			,pos-e-2oc192-sm-vlr-sc(1979)		-- GSR Edge 2 Port Packet Over Sonet OC-192, Single Mode, Very Long Reach, SC Connector Card  %DNP% until Jan 2004, contact srinud
			,pos-e-2oc192-sm-vlr-fc(1980)		-- GSR Edge 2 Port Packet Over Sonet OC-192, Single Mode, Very Long Reach, FC Connector Card  %DNP% until Jan 2004, contact srinud
			,pos-e-2oc192-sm-elr-fc(1981)		-- GSR Edge 2 Port Packet Over Sonet OC-192, Single Mode, Extremely Long Reach, FC Connector Card %DNP% until Jan 2004, contact srinud  
			,pos-e-2oc192-sm-elr-sc(1982)		-- GSR Edge 2 Port Packet Over Sonet OC-192, Single Mode, Extremely Long Reach, SC Connector Card %DNP% until Jan 2004, contact srinud
			,iad2430-ob-8fxs(1983)			-- This card provides 8 on-board analog Foreign Exchange Stations (FXS) in the Integrated Access Device 2430 (IAD2430) chassis
			,iad2430-ob-16fxs(1984)			-- This card provides 16 on-board analog Foreign Exchange Stations (FXS) in the Integrated Access Device 2430 (IAD2430) chassis
			,iad2430-ob-24fxs(1985)			-- This card provides 24 on-board analog Foreign Exchange Stations (FXS) in the Integrated Access Device 2430 (IAD2430) chassis
			,iad2430-ob-t1e1(1986)			-- This card provides on-board T1/E1 in the Integrated Access Device 2430 (IAD2430) chassis.

--	2000-2049:	more c38xx cards		%DNP%
			,mc3810-hcm5(2000)			--  High performance compression module for the MC3810 platform equipped with five TI 549 DSPs
--	2050-2099:	10000Bases Cards		%DNP%
			,m10000base-sxp(2050)			-- Cisco parallel 860nm Laser 10 gigabit ethernet port adapter %DNP% Not in Use
			,m10000base-lx4(2051)			--  Cisco Wide-WDM 1310nm Laser 10 gigabit ethernet port adapter 
			,m10000base-ex4(2052)			--  Cisco Wide-WDM 1550nm Laser 10 gigabit ethernet port adapter 
			,m10000base-lr(2053)			--  Cisco Serial 1310nm Laser 10 gigabit ethernet port adapter 
			,m10000base-er(2054)			-- Cisco Serial 1550nm Laser 10 gigabit ethernet port adapter 
			,m10000base-sx4(2055)			-- Cisco Wide-WDM 850nm Laser 10 gigabit ethernet port adapter 

--       2100-2150:   more c7xxx cards                %DNP%                  
			,c7401(2100)				-- Cisco 7400 Family, 1 Slot Router %DNP% until Feb 2001, contact taz 
			,io-c7401-ge(2101)			-- Cisco 7401 I/O Controller with dual 10/100/1000Mbps GE interfaces %DNP% until Feb 2001, contact taz
			,sa-ahdlc-comp(2102)			-- Asynchronous HDLC adaptor with compression support %DNP% until Jan 2002, contact bobbys alankp
			,c7300-4oc3-pos-mm(2103)		-- 4-port OC3 POS line card for Cisco 7300, Multimode %DNP% until Oct 2001, contact yoko
			,c7300-4oc3-pos-sm-ir(2104)		-- 4-port OC3 POS line card for Cisco 7300, Singlemode, Intermediate Reach %DNP% until Oct 2001, contact yoko
			,c7300-4oc3-pos-sm-lr(2105)		-- 4-port OC3 POS line card for Cisco 7300, Singlemode, Long Reach %DNP% until Oct 2001, contact yoko
			,c7300-oc48-pos-sm-sr(2106)		-- 1-port OC48 POS line card for Cisco 7300, Singlemode, Short Reach %DNP% until Oct 2001, contact yoko
			,c7300-oc48-pos-sm-ir(2107)		-- 1-port OC48 POS line card for Cisco 7300, Singlemode, Intermediate Reach %DNP% until Oct 2001, contact yoko
			,c7300-oc48-pos-sm-lr(2108)		-- 1-port OC48 POS line card for Cisco 7300, Singlemode, Long Reach %DNP% until Oct 2001, contact yoko
			,c7300-6t3(2109)			-- 6-port T3 line card for Cisco 7300 with DSU %DNP% until Feb 2002, contact yoko
			,c7300-12t3(2110)			-- 12-port T3 line card for Cisco 7300 with DSU %DNP% until Feb 2002, contact yoko
			,c7300-4oc3-atm-mm(2111)		-- 4-port OC3 ATM line card for Cisco 7300, Multimode %DNP% until Feb 2002, contact yoko
			,c7300-4oc3-atm-sm-ir(2112)		-- 4-port OC3 ATM line card for Cisco 7300, Singlemode, Intermediate Reach %DNP% until Feb 2002, contact yoko
			,c7300-4oc3-atm-sm-lr(2113)		-- 4-port OC3 ATM line card for Cisco 7300, Singlemode, Long Reach %DNP% until Feb 2002, contact yoko
			,c7300-2oc12-pos-mm(2114)		-- 2-port OC12 POS line card for Cisco 7300, Multimode %DNP% until Feb 2002, contact yoko
			,c7300-2oc12-pos-sm-ir(2115)		-- 2-port OC12 POS line card for Cisco 7300, Singlemode, Intermediate Reach %DNP% until Feb 2002, contact yoko
			,c7300-2oc12-pos-sm-lr(2116)		-- 2-port OC12 POS line card for Cisco 7300, Singlemode, Long Reach %DNP% until Feb 2002, contact yoko
			,c7300-oc48-srp-sm-sr(2117)		-- OC48 SRP line card for Cisco 7300, Singlemode, Short Reach %DNP% until Feb 2002, contact yoko
			,c7300-oc48-srp-sm-lr(2118)		-- OC48 SRP line card for Cisco 7300, Singlemode, Long Reach %DNP% until Feb 2002, contact yoko
			,c7300-oc12-pos-mm(2119)		-- 1-port OC12 POS line card for Cisco 7300, MultiMode %DNP% until Feb 2002, contact yoko
			,c7300-oc12-pos-sm-ir(2120)		-- 1-port OC12 POS line card for Cisco 7300, Single Mode,Intermediate Reach %DNP% until Feb 2002, contact yoko
			,c7300-oc12-pos-sm-lr(2121)		-- 1-port OC12 POS line card for Cisco 7300, Single Mode, Long Reach %DNP% until Feb 2002, contact yoko
			,c7300-2oc3-pos-mm(2122)		-- 2-port OC3 POS line card for Cisco 7300, Multi Mode %DNP% until Apr 2002, contact yoko
			,c7300-2oc3-pos-sm-ir(2123)		-- 2-port OC3 POS line card for Cisco 7300, Single Mode, Intermediate Reach %DNP% until Apr 2002, contact yoko	
			,c7300-2oc3-pos-sm-lr(2124)		-- 2-port OC3 POS line card for Cisco 7300, Single Mode, Long Reach %DNP% until Apr 2002, contact yoko
			,c7300-2oc3-atm-mm(2125)		-- 2-port OC3 ATM line card for Cisco 7300, Multi Mode %DNP% until Apr 2002, contact yoko
			,c7300-2oc3-atm-sm-ir(2126)		-- 2-port OC3 ATM line card for Cisco 7300, Single Mode, Intermediate Reach %DNP% until Apr 2002, contact yoko
			,c7300-2oc3-atm-sm-lr(2127)		-- 2-port OC3 ATM line card for Cisco 7300, Single Mode, Long Reach %DNP% until Apr 2002, contact yoko
			,c7411-npeg1(2128)			-- Cisco 7400 Family, 1 Slot Router
			,io-c7411-ge(2129)			-- Cisco 7411 I/O Controller with three 10/100/1000Mbps GE interfaces
			,c7301-npeg1(2130)			-- Cisco 7300 Family, 1 Slot Router %DNP% until Jan 2003, contact dhom
			,io-c7301-ge(2131)			-- Cisco 7301 I/O Controller with three 10/100/1000Mbps GE interfaces %DNP% until Jan 2003, contact dhom
			,vip6-80(2132)				-- A new VIP card to be used in 7500 box. this card is same as VIP4-80 but with a higher speed CPU.
			,pa-a6-mm-oc3(2133)			-- ATM WAN OC3 MM Port Adapter. 
			,pa-a6-smi-oc3(2134)			-- ATM WAN OC3 SMI Port Adapter. 
			,pa-a6-sml-oc3(2135)			-- ATM WAN OC3 SML Port Adapter. 
			,pa-a6-ds3-oc3(2136)			-- ATM WAN OC3 DS3 Port Adapter. 
			,pa-a6-e3-oc3(2137)			-- ATM WAN OC3 E3 Port Adapter. 
			,c7300-cc-pa(2138)			-- Port Adaptor Carrier Card for Cisco 7304
			,c7304-msc-100(2139)			-- C7304-MSC-100 is a carrier card for 7304. it can carry up to 2 VPA (Versatile Port Adaptor) cards %DNP% until Jan 2004, contact chanm, bsou
			,c7300-6e3(2140)			-- 6-port E3 interface line card for Cisco 7300 %DNP% until Jan 2004, contact chanm yega

--	2151-2199:	C7160 cards			%DNP%
			,c7160-2fe-1ge(2151)			-- IO card for the C7160 family with 2 10/100 fast ethernet interfaces and 1 10/100/1000 GE interface %DNP% until Nov 2001, contact ahase
			,c7160-4fe(2152)			-- IO card for the C7160 family with 4 10/100 FE ports %DNP% until Nov 2001, contact ahase
			,c7160-2ge(2153)			-- IO card for the C7160 family with 2 GE ports %DNP% until Nov 2001, contact ahase
			,c7160-1ge(2154)			-- IO card for the C7160 family with 1 high performance GE port %DNP% until Nov 2001, contact ahase
--	2200-2249:	yet more BFR cards		%DNP%
			,gsr-1p10ge(2200)			-- One Port 10 Gigabit Ethernet Card for the 12000 series routers
			,gsr-e48-pos-oc48-sm-ir-sc(2201)	-- GSR, Edge Engine, OC48 POS, Single Mode, Intermediate Reach, SC Connector %DNP% until Aug 2001, contact zuobing
			,gsr-dtp-dense48(2202)			-- A dual mode card. It can function as a 4xOC48 or 2xSRP48 %DNP% until Nov 2001, contact hfanous
			,gsr-e-oc192-sm-lr-sc(2203)		-- GSR Edge 1 Port Packet over Sonet OC-192, Single Mode, Long Reach, SC Connector card
			,gsr-e-oc192-sm-vsr-sc(2204)		-- GSR Edge 1 Port Packet over Sonet OC-192, Single Mode, Very Short Reach, SC Connector card
			,gsr-e-oc192-sm-vsr-fc(2205)		-- GSR Edge 1 Port Packet over Sonet OC-192, Single Mode, Very Short Reach, FC Connector card
			,gsr-e-oc192-sm-sr-fc(2206)		-- GSR Edge 1 Port Packet over Sonet OC-192, Single Mode, Short Reach, FC Connector card
			,gsr-e-oc192-sm-sr-sc(2207)		-- GSR Edge 1 Port Packet over Sonet OC-192, Single Mode, Short Reach, SC Connector card
			,gsr-e-oc192-sm-lr-fc(2208)		-- GSR Edge 1 Port Packet over Sonet OC-192, Single Mode, Long Reach, FC Connector card
			,gsr-e-qoc48-sm-lr-fc(2209)		-- GSR Edge 4 Port Packet over Sonet OC-48, Single Mode, Long Reach, FC Connector card
			,gsr-e-qoc48-sm-lr-sc(2210)		-- GSR Edge 4 Port Packet over Sonet OC-48, Single Mode, Long Reach, SC Connector card
			,gsr-e-qoc48-sm-vsr-sc(2211)		-- GSR Edge 4 Port Packet over Sonet OC-48, Single Mode, Very Short Reach, SC Connector card
			,gsr-e-qoc48-sm-vsr-fc(2212)		-- GSR Edge 4 Port Packet over Sonet OC-48, Single Mode, Very Short Reach, FC Connector card
			,gsr-e-qoc48-sm-sr-fc(2213)		-- GSR Edge 4 Port Packet over Sonet OC-48, Single Mode, Short Reach, FC Connector card
			,gsr-e-qoc48-sm-sr-sc(2214)		-- GSR Edge 4 Port Packet over Sonet OC-48, Single Mode, Short Reach, SC Connector card
			,gsr-e-qoc48-vsr(2215)			-- GSR Edge 4 Port Packet over Sonet OC-48, Very Short Reach
			,gsr-e-qoc48-sm-sr2-sc(2216)		-- GSR Edge 4 Port Packet over Sonet OC-48, Single Mode, Short Reach 2, SC Connector card
			,gsr-e-qoc48-sm-sr2-fc(2217)		-- GSR Edge 4 Port Packet over Sonet OC-48, Single Mode, Short Reach 2, FC Connector card
			,gsr-e-qoc48-mm-sr-sc(2218)		-- GSR Edge 4 Port Packet over Sonet OC-48, Multi Mode, Short Reach, SC Connector card
			,gsr-e-qoc48-sm-ir-sc(2219)		-- GSR Edge 4 Port Packet over Sonet OC-48, Single Mode, Intermediate Reach, SC Connector card
			,gsr-e-qoc48-sm-ir-fc(2220)		-- GSR Edge 4 Port Packet over Sonet OC-48, Single Mode, Intermediate Reach, FC Connector card
			,gsr-e-qoc48-sm-vlr-sc(2221)		-- GSR Edge 4 Port Packet over Sonet OC-48, Single Mode, Very Long Reach, SC Connector card
			,gsr-e-qoc48-sm-vlr-fc(2222)		-- GSR Edge 4 Port Packet over Sonet OC-48, Single Mode, Very Long Reach, FC Connector card
			,gsr-e-qoc48-sm-elr-sc(2223)		-- GSR Edge 4 Port Packet over Sonet OC-48, Single Mode, Extremely Long Reach, SC Connector card
			,gsr-e-qoc48-sm-elr-fc(2224)		-- GSR Edge 4 Port Packet over Sonet OC-48, Single Mode, Extremely Long Reach, FC Connector card
			,gsr-e-oc192-vsr(2225)			-- GSR Edge 1 Port Packet over Sonet OC-192, Very Short Reach
			,gsr-e-oc192-sm-sr2-sc(2226)		-- GSR Edge 1 Port Packet over Sonet OC-192, Single Mode, Short Reach 2, SC Connector card
			,gsr-e-oc192-sm-sr2-fc(2227)		-- GSR Edge 1 Port Packet over Sonet OC-192, Single Mode, Short Reach 2, FC Connector card
			,gsr-e-oc192-mm-sr-sc(2228)		-- GSR Edge 1 Port Packet over Sonet OC-192, Multi Mode, Short Reach, SC Connector card
			,gsr-e-oc192-sm-ir-sc(2229)		-- GSR Edge 1 Port Packet over Sonet OC-192, Single Mode, Intermediate Reach, SC Connector card
			,gsr-e-oc192-sm-ir-fc(2230)		-- GSR Edge 1 Port Packet over Sonet OC-192, Single Mode, Intermediate Reach, FC Connector card
			,gsr-e-oc192-sm-vlr-sc(2231)		-- GSR Edge 1 Port Packet over Sonet OC-192, Single Mode, Very Long Reach, SC Connector card
			,gsr-e-oc192-sm-vlr-fc(2232)		-- GSR Edge 1 Port Packet over Sonet OC-192, Single Mode, Very Long Reach, FC Connector card
			,gsr-e-oc192-sm-elr-sc(2233)		-- GSR Edge 1 Port Packet over Sonet OC-192, Single Mode, Extremely Long Reach, SC Connector card
			,gsr-e-oc192-sm-elr-fc(2234)		-- GSR Edge 1 Port Packet over Sonet OC-192, Single Mode, Extremely Long Reach, FC Connector card
			,gsr-csc12404(2235)			-- GSR 12404 Fabric and Alarm card %DNP% until Jul 2001, contact mrishik
			,ssrp-2oc48-srp-sm-sr-lc(2236)		-- GSR 2 port SONET dual SRP/POS OC-48c/STM-16, SRP Mode, Single Mode, Short Reach, LC Connector card
			,ssrp-2oc48-srp-sm-ir-lc(2237)		-- GSR 2 port SONET dual SRP/POS OC-48c/STM-16, SRP Mode, Single Mode, Intermediate Reach, LC Connector card
			,ssrp-2oc48-srp-sm-lr-lc(2238)		-- GSR 2 port SONET dual SRP/POS OC-48c/STM-16, SRP Mode, Single Mode, Long Reach, LC Connector card
			,ssrp-2oc48-pos-sm-sr-lc(2239)		-- GSR 2 port SONET dual SRP/POS OC-48c/STM-16, POS Mode, Single Mode, Short Reach, LC Connector card
			,ssrp-2oc48-pos-sm-ir-lc(2240)		-- GSR 2 port SONET dual SRP/POS OC-48c/STM-16, POS Mode, Single Mode, Intermediate Reach, LC Connector card
			,ssrp-2oc48-pos-sm-lr-lc(2241)		-- GSR 2 port SONET dual SRP/POS OC-48c/STM-16, POS Mode, Single Mode, Long Reach, LC Connector card
			,gsr-10pge-b(2242)			-- Ten port Gigabit Ethernet card for the 12000 series of routers. The line card has switching Engine 4 with TxPlus on the transmit side %DNP% until Nov 2001, contact ashokt
			,gsr-e48-pos-qoc12-mm-sr-sc(2243)	-- GSR edge48 Quad OC-12 (concanenated) POS card, Multi Mode (fiber), Short Reach, SC connector %DNP% Nov 2001, conatct zuobing
			,gsr-gefe(2244)				-- Modular Gigabit/Fast Ethernet card for GSR 
			,gsr-pa-1ge(2245)			-- 1 Port Gigabit Ethernet Port Adapter Of Modular Gigabit/Fast Ethernet card for GSR %DNP% until Jan 2002, contact kmdhar
			,gsr-pa-3ge(2246)			-- 3 Port Gigabit Ethernet Port Adapter Of Modular Gigabit/Fast Ethernet card for GSR 
			,gsr-pa-24fe(2247)			-- 24 Port Fast Ethernet Port Adapter Of Modular Gigabit/Fast Ethernet card for GSR 
			,gsr-e48-atm-4oc12-sm-ir-sc(2248)	-- Edge Engine 48, ATM, 4 ports OC12/STM4, Single Mode, Intermediate Reach, SC connector
			,gsr-e48-atm-4oc12-mm-sr-sc(2249)	-- GSR, Edge Engine 48, ATM, 4 ports OC12/STM4, Multi Mode, Short Reach, SC connector
--	2250-2299:	more  Wide Area Switch Back Cards/Line Modules		%DNP%
			,lm-rpm-xf-ui(2250)			-- Management back card for RPM-XF with 2 RJ-45 RS232 ports and 2 Fast Ethernet Ports %DNP% until Nov 2001, contact bkundass
			,lm-pos-1oc12(2251)			-- 1 port OC-12 Packet Over Sonet back card for RPM-XF (Route Processor Module Express Forwarding) %DNP% until Nov 2001, contact bkundass
			,lm-rpm-xf-1ge(2252)			-- 1 port GIgabit Ethernet back card for RPM-XF (Route Processor Module Express Forwarding) with SFF connector %DNP% until Nov 2001, contact bkundass
			,lm-1fe-txcp(2253)			-- 1 port Fast Ethernet RJ-45 connector back card with co-processor assist for the MGX8800 RPM PR module %DNP% until Dec 2001, contact dblanken
			,lm-smfir-8oc3c(2254)			-- 8 port, 155Mbps, SMFIR-8-155LC/C (Intermediate Reach) Back Card, LC Connector %DNP% until Jan 2002, contact wwcai
			,lm-smflr-8oc3c(2255)			-- 8 port, 155Mbps, SMFLR-8-155LC/C (Long Reach) Back Card, LC Connector %DNP% until Jan 2002, contact wwcai
			,lm-mmf-8oc3c(2256)			-- 8 port, 155Mbps, MMF-8-155C Back Card, LC Connector %DNP% until Jan 2002, contact wwcai
			,lm-smfir-1oc3(2257)			-- 1 port, 155Mbps, SMFIR-1-155 (Intermediate Reach) Back Card %DNP% until Jan 2002, contact wwcai
			,lm-smflr-1oc3(2258)			-- 1 port, 155Mbps, SMFLR-1-155 (Long Reach) Back Card %DNP% until Jan 2002, contact wwcai
			,lm-smb-1stm1(2259)			-- MGX SMB 1 port STM1 Back Card %DNP% until Jan 2002, contact wwcai
			,lm-scsi2b-2hssi(2260)			-- Two HSSI SCSI-2/B Back Card %DNP% until Jan 2002, contact wwcai
			,lm-12in1-8s(2261)			-- 12In1-8s Back Card %DNP% until Jan 2002, contact wwcai
			,lm-smb-6e3(2262)			-- 6 E3 ports SMB Back Card %DNP% until Jan 2002, contact wwcai
			,lm-combo-t3e3-oc3(2263)		-- PXM1E-COMBO-T3E3-155'S Back Card supporting 8 T3/E3 ports and 4 OC3 ports  %DNP% until Jan 2002, contact wwcai
			,lm-rj48-16t1e1(2264)			-- Sixteen T1/E1 RJ-48 Back Card %DNP% until Feb 2002, contact wwcai
			,lm-smf-ir-2oc12c(2265)			-- 2 port, 622Mbps, SMFIR-2-622LC/C (Intermediate Reach) Back Card, LC Connector %DNP% until Jan 2002, contact wwcai
			,lm-smf-lr-2oc12c(2266)			-- 2 port, 622Mbps, SMFLR-2-622LC/C (Long Reach) Back Card, LC Connector %DNP% until Jan 2002, contact wwcai
--	3000-3049:	more yet more BFR cards              %DNP%
			,gsr-e48-atm-4oc3-sm-ir-sc(3000)	-- GSR, Edge Engine 48, ATM, 4 ports OC3/STM1, Single Mode, Intermediate reach, SC connector %DNP% until Aug 2003, contact hbarilan
			,gsr-e48-atm-4oc3-mm-sr-sc(3001)	-- GSR, Edge Engine 48, ATM, 4 ports OC3/STM1, Multi Mode, Short Reach, SC connector %DNP% until Aug 2003, contact hbarilan
			,gsr-e48-pos-4oc3-mm-sr-mtrj(3002)	-- GSR, Edge Engine 48, 4 port concatenated OC3 POS, Muti-mode, Short reach, MT-RJ connector %DNP% until Apr 2002, contact jhzhao
			,gsr-e48-pos-4oc3-sm-ir-lc(3003)	-- GSR, Edge Engine 48, 4 port concatenated OC3 POS, Singlemode, Intermediate reach, LC connector %DNP% until Apr 2002, contact jhzhao
			,gsr-e48-pos-4oc3-sm-lr-lc(3004)	-- GSR, Edge Engine 48, 4 port concatenated OC3 POS, Singlemode, Long reach, LC connector %DNP% until Apr 2002, contact jhzhao
			,gsr-e48-pos-8oc3-mm-sr-mtrj(3005)	-- GSR, Edge Engine 48, 8 port concatenated OC3 POS, Muti-mode, Short reach, MT-RJ connector %DNP% until Apr 2002, contact jhzhao
			,gsr-e48-pos-16oc3-mm-sr-mtrj(3006)	-- GSR, Edge Engine 48, 16 port concatenated OC3 POS, Muti-mode, Short reach, MT-RJ connector %DNP% until Apr 2002, contact jhzhao
			,gsr-e48-pos-8oc3-sm-ir-lc(3007)	-- GSR, Edge Engine 48, 8 port concatenated OC3 POS, Singlemode, Intermediate reach, LC connector %DNP% until Apr 2002, contact jhzhao
			,ssrp-e48-2oc12-sm-ir(3008)		-- GSR 2 port SONET based SRP OC-12c/STM-4 Single mode Intermediate reach line card 
			,ssrp-e48-2oc12-sm-xr(3009)		-- GSR 2 port SONET based SRP OC-12c/STM-4 Single mode Extented reach line card 
			,ssrp-e48-1oc12-sm-ir(3010)		-- GSR 1 port SONET based SRP OC-12c/STM-4 Single mode Intermediate reach line card 
			,ssrp-e48-1oc12-sm-xr(3011)		-- GSR 1 port SONET based SRP OC-12c/STM-4 Single mode Extented reach line card 
			,gsr-csc12816(3012)			-- GSR 12816 Clock Scheduler Card %DNP% unitl Dec 2002, contact honyang, fyuan
			,gsr-csc12810(3013)			-- GSR 12810 Clock Scheduler Card %DNP% unitl Dec 2002, contact honyang, fyuan
			,gsr-sfc12810(3014)			-- GSR 12810 Switch Fabric Card %DNP% unitl Dec 2002, contact honyang, fyuan
			,gsr-sfc12816(3015)			-- GSR 12816 Switch Fabric Card %DNP% unitl Dec 2002, contact honyang, fyuan
			,gsr-e192-common-engine(3016)		-- GSR Edge 192 Common Engine Card  %DNP% until Oct 2002, contact slegault
			,gsr-1p10ge-xro(3017)			--One port 10Gigabit Ethernet linecard with Extended Reach Optics for the 12000 series routers 
			,gsr-4pge(3018)				-- Tetra card Edge engine 3 - 4 port Gigabit Ethernet card %DNP% until Feb 2003, contact ravindra
			,gsr-2oc192-pos(3019)			-- GSR 2 Port Packet Over Sonet OC-192c/STM-64 line card %DNP% until Jan 2004 contact srinud
			,gsr-8oc48-pos(3020)			-- GSR 8 Port Packet Over Sonet OC-48/STM-16 line card %DNP% until Jan 2004 contact srinud

--  	3050-3099:       more Wide Area Switch common cards (MGX, IGX series boxes)   %DNP%
			,vism-pr-8e1(3050)			-- Voice Interworking Service Module Premium Card (VISM-PR) with 8 E1 ports
			,vxsm-4oc3(3051)			-- Voice switch service module, 4 port OC3/STM-1 compliant
			,mgx-srm-4oc3(3052)			-- MGX88xx voice service redundancy module, used to providing 1:N redundancy for 4 OC3

--	4000-4049:	yet more 16xx, 26xx, & 36xx cards	%DNP%
			,nm-ceoip-4Serial(4000)			-- Four port Serial Interface Circuit Emulation over IP network module %DNP% until Jul 2003, contact ssamant
			,nm-1a-oc3mm-ep(4001)			-- Enhanced Performance ATM OC3, multimode network module %DNP% until Nov 2002, contact jantony
			,nm-1a-oc3smi-ep(4002)			-- Enhanced Performance ATM OC3, intermediate reach single mode network module %DNP% until Nov 2002, contact jantony
			,nm-1a-oc3sml-ep(4003)			-- Enhanced Performance ATM OC3, long reach single mode network module %DNP% until Nov 2002, contact jantony
			,nm-cids(4004)				-- Intrusion Detection Sensor Module in NM form factor for 36xx/37xx/26xx family branch routers %DNP% until Jun 2003, contact joeolson
			,nm-hd-1v(4005)				-- High Density Network Module with one vic slot. %DNP% until Dec 2002, contact nipa
			,nm-hd-2v(4006)				-- High Density Network Module with two vic slots. %DNP% until Dec 2002, contact nipa
			,nm-hd-2ve(4007)			-- Enhanced High Density Network Module with two vic slots. %DNP% until Dec 2002, contact nipa
			,vic2-fxs2(4008)			-- 2nd generation two port FXS(Foreign Exchange station) voice interface card. %DNP% until Dec 2002, contact nipa
			,vic2-fxo2(4009)			-- 2nd generation two port FXO(Foreign Exchange Office) voice interface card. %DNP% until Dec 2002, contact nipa
			,vic2-fxo4(4010)			-- 2nd generation four port FXO(Foreign Exchange Office) voice interface card. %DNP% until Dec 2002, contact nipa
			,vic2-em2(4011)			-- 2nd generation two port EM(Ear & Mouth) voice interface card. %DNP% until Dec 2002, contact nipa
			,vic2-bri2(4012)			-- 2nd generation two port BRI(Basic Rate Interface) voice interface card. %DNP% until Dec 2002, contact nipa
			,vic2-cama2(4013)			-- 2nd generation two port CAMA(Centralized Automated Message accounting) voice interface card supporting 911 calls. %DNP% until Dec 2002, contact nipa
			,hwic-1ge-sfp(4014)			-- Single port Gigabit Ethernet high-speed WAN interface card (HWIC) with Small Formfactor Pluggable (SFP) transceiver %DNP% until Apr 2004, contact jenniel
			,hd-dsp(4015)				-- 5510 Digital Signal Processor on NM-HD-1V,NM-HD-2V and NM-HD-2VE
			,hdv2-port0(4016)			-- High Density Network module-2 with no onboard interface %DNP% until Jul 2003, contact dobro-snmp
			,hdv2-port2(4017)			-- High Density Network module-2 with onboard two port T1/E1 interface  %DNP% until Jul 2003, contact dobro-snmp
			,hdv2-port1(4018)			-- High Density Network module-2 with onboard one port T1/E1 interface  %DNP% until Jul 2003, contact dobro-snmp
			,nm-nam(4019)				--  Network Analysis Module (NAM) network module for the 2600/3600/3700 router families %DNP% until Dec 2003, contact joeolson

--	4050-4099:	More Catalyst 6000 Cards		%DNP%
			,cat6k-ws-sup720(4050)		-- Catalyst 6500 Supervisor Module 720 CPU board %DNP% until May 2003, contact lpbinh tjw fxu
			,cat6k-ws-sup720-base(4051)	-- Catalyst 6500 Supervisor Module 720 base board %DNP% until May 2003, contact lpbinh tjw fxu
			,cat6k-wsx-6802-10ge(4052)        -- Catalyst 6500 2 port 10 GE %DNP% until Dec 2003, contact lpbinh tjw fxu
			,cat6k-wsx-6832-sfp(4053)        -- Catalyst 6500 32 port 1000Base FX (SFP GBIC) %DNP% until Dec 2003, contact lpbinh tjw fxu
			,cat6k-wsx-6748-getx(4054)        -- Catalyst 6500 48 port 10/100/1000 (RJ-45) %DNP% until Dec 2003, contact lpbinh tjw fxu
			,cat6k-wsx-6704-10ge(4055)        -- Catalyst 6500 4 port 10 GE %DNP% until Dec 2003, contact lpbinh tjw fxu
			,cat6k-wsx-6748-sfp(4056)        -- Catalyst 6500 48 port 1000Base FX (SFP GBIC) %DNP% until Dec 2003, contact lpbinh tjw fxu
			,cat6k-wsx-6724-sfp(4057)        -- Catalyst 6500 24 port 1000Base FX (SFP GBIC) %DNP% until Dec 2003, contact lpbinh tjw fxu
			,cat6k-wsf-6k-pfc(4058)        --  Catalyst 6500 L3 switching engine 
			,cat6k-wsf-6k-pfc2(4059)        -- Catalyst 6500 L3 switching engine II  
			,cat6k-wsf-6k-dfc(4060)        -- Catalyst 6500 distributed switching engine 
			,cat6k-wsf-6k-pfc3a(4061)        -- Catalyst 6500 Centralized L3 switching engine IIIa  %DNP% until May 2003, contact lpbinh tjw fxu
			,cat6k-wsf-6k-dfc3a(4062)        -- Catalyst 6500 Distributed L3 switching engine IIIa  %DNP% until May 2003, contact lpbinh tjw fxu
			,cat6k-wsx-6148-ge-tx(4063)	-- Catalyst 6000 48 port10/100/1000BaseT(RJ-45) module 
			,cat6k-wsx-6148-rj21(4064)	-- Catalyst 6000 48 port10/100BaseTX(RJ-21) module 
			,cat6k-wsx-6148-rj45(4065)	-- Catalyst 6000 48 port10/100BaseTX(RJ-45) module 
			,cat6k-wsx-6548-getx(4066)	-- Catalyst 6500 48 port 10/100/1000 (RJ-45) %DNP% until May 2003, contact lpbinh tjw fxu
			,cat6k-wsf-6700-dfc3(4067)	-- Catalyst 6500 Distributed L3 switching engine III %DNP% until Oct 2003, contact wenxu
			,cat6k-wsx-6324-100fx-sm(4068)	-- 24-port 100FX single mode MT-RJ with 128K per-port packet buffer %DNP% until May 2003, contact lpbinh, tjw, fxu
			,cat6k-ws-svc-idsm2(4069)       -- Catalyst 6500 Intrusion Detection Module
			,cat6k-ws-svc-idsupg(4070)      -- Catalyst 6500 IDS 2 accelerator board

			,oc3-sfp(4100)			-- Oc3 Small Form Factor Pluggable Optics(SFP)
			,oc12-sfp(4101)			-- Oc12 Small Form Factor Pluggable Optics(SFP)
			,osm-2oc48-pos-ss(4102)		-- Optical Service Module, 2-Port OC48 POS, Single-mode, Short-reach with 4 Gigabit Ethernet ports
			,osm-2oc48-pos-si(4103)			-- Optical Service Module, 2-Port OC48 POS Single-mode, Intermediate-reach with 4 Gigabit Ethernet ports
			,osm-2oc48-pos-sl(4104)		-- Optical Service Module, 2-Port OC48 POS Single-mode, Long-reach with 4 Gigabit Ethernet ports
			,osm-1oc48-srp-ss(4105)		-- Optical Service Module, 1-Port OC48 SONET based SRP,Single-mode, Short-reach with 4 Gigabit Ethernet ports
			,osm-1oc48-srp-si(4106)		-- Optical Service Module, 1-Port OC48 SONET based SRP,Single-mode, Intermediate-reach with 4 Gigabit Ethernet ports
			,osm-1oc48-srp-sl(4107)		-- Optical Service Module, 1-Port OC48 SONET based SRP,Single-mode, Long-reach with 4 Gigabit Ethernet ports
			,oc48-sfp(4108)			-- OC48 Small Form Factor Pluggable Optics(SFP) %DNP% until Jun 2003, contact rramacha
			,oc3-oc12-sfp(4109)		-- Dual rate OC3/OC12 Small Form Factor Pluggable Optics(SFP) %DNP% until Jun 2003, contact rramacha
			,oc3-oc12-oc48-sfp(4110)	-- Multi-rate OC3/OC12/OC48 Small Form Factor Pluggable Optics(SFP) %DNP% until Jun 2003, contact rramacha
			,cat375048-ps(4111)		-- 48 10/100 In-Line Power Ethernet ports + 2 Gigabit Ethernet SFP ports Layer 2/Layer 3 Module.(SFP Small Form factor Plugable)  %DNP% until Jul 2003, contact rneal 
			,cat375024-ps(4112)		-- 24 10/100 In-Line Power Ethernet ports + 4 Gigabit Ethernet SFP ports Layer 2/Layer 3 Module.(SFP Small Form factor Plugable)  %DNP% until Jul 2003, contact rneal
			,pwr-ac-465w(4113)			-- Cisco 465W AC Power Supply.
			,base-sx-1000-sfp(4114)			-- Short wavelength gigabit ethernet SFP. %DNP% until Apr 2004, contact jenniel
			,base-lx-1000-sfp(4115)			-- Long wavelength gigabit ethernet SFP. %DNP% until Apr 2004, contact jenniel
			,base-t-1000-sfp(4116)			-- copper gigabit ethernet SFP. %DNP% until Apr 2004, contact jenniel
			,base-zx-1000-sfp(4117)			-- Extended reach gigabit ethernet SFP. %DNP% until Apr 2004, contact jenniel
			,cwdm-1470-sfp(4118)			-- 1470nm color coded CWDM SFP. %DNP% until Apr 2004, contact jenniel
			,cwdm-1490-sfp(4119)			-- 1490nm color coded CWDM SFP. %DNP% until Apr 2004, contact jenniel
			,cwdm-1510-sfp(4120)			-- 1510nm color coded CWDM SFP. %DNP% until Apr 2004, contact jenniel
			,cwdm-1530-sfp(4121)			-- 1530nm color coded CWDM SFP. %DNP% until Apr 2004, contact jenniel
			,cwdm-1550-sfp(4122)			-- 1550nm color coded CWDM SFP. %DNP% until Apr 2004, contact jenniel
			,cwdm-1570-sfp(4123)			-- 1570nm color coded CWDM SFP. %DNP% until Apr 2004, contact jenniel
			,cwdm-1590-sfp(4124)			-- 1590nm color coded CWDM SFP. %DNP% until Apr 2004, contact jenniel
			,cwdm-1610-sfp(4125)			-- 1610nm color coded CWDM SFP. %DNP% until Apr 2004, contact jenniel
			,base1000-lh-sfp(4126)			-- long haul gigabit ethernet SFP. %DNP% until Apr 2004, contact jenniel
			,base1000-cx-sfp(4127)			-- copper wire gigabit ethernet SFP. %DNP% until Apr 2004, contact jenniel

--	4151-4200:	c32xx Cards		%DNP%
			,c3220-smic(4151)			-- Serial Mobile Interface Card(SMIC) for the C3220 Mobile Access Router with 2 Serial Interfaces. %DNP% until May 2003, contact pnoone
			,c3220-fe-smic(4152)			-- Fast Ethernet Switch Mobile Interface Card(FESMIC) for the C3220 Mobile Access Router with 2 Fast Ethernet Interfaces. %DNP% until May 2003, contact pnoone
			,cat6k-wsx-6302a-msm(4153)		-- Multilayer Switch Module (Rev. A)  for the Catalyst 6000 series %DNP% until May 2003, contact lpbinh tjw fxu
 			,c356024-ps(4250)			-- 24 10/100 In-Line Power Ethernet ports + 2 Gigabit Ethernet SFP ports Layer 2/Layer 3 Module.(SFP Small Form factor Pluggable) %DNP% until Oct 2003, contact rneal
 			,c356048-ps(4251)			-- 48 10/100 In-Line Power Ethernet ports + 4 Gigabit Ethernet SFP ports Layer 2/Layer 3 Module.(SFP Small Form factor Pluggable) %DNP% until Oct 2003, contact rneal

			}
                   ACCESS  read-only
                   STATUS  deprecated
                   DESCRIPTION
                           "Functional type of this card."
                   ::= { cardTableEntry 2 }

               cardDescr OBJECT-TYPE
                   SYNTAX  DisplayString
                   ACCESS  read-only
                   STATUS  deprecated
                   DESCRIPTION
                           "Text description of this card."
                   ::= { cardTableEntry 3 }

               cardSerial OBJECT-TYPE
                   SYNTAX  INTEGER
                   ACCESS  read-only
                   STATUS  deprecated
                   DESCRIPTION
                           "The serial number of this card, or zero if
                           unavailable."
                   ::= { cardTableEntry 4 }

               cardHwVersion OBJECT-TYPE
                   SYNTAX  DisplayString
                   ACCESS  read-only
                   STATUS  deprecated
                   DESCRIPTION
                           "Hardware revision level of this card, or an
                           empty string if unavailable."
                   ::= { cardTableEntry 5 }

               cardSwVersion OBJECT-TYPE
                   SYNTAX  DisplayString
                   ACCESS  read-only
                   STATUS  deprecated
                   DESCRIPTION
                           "Version of the firmware or microcode
                           installed on this card, or an empty string if
                           unavailable."
                   ::= { cardTableEntry 6 }

               cardSlotNumber OBJECT-TYPE
                   SYNTAX  INTEGER
                   ACCESS  read-only
                   STATUS  deprecated
                   DESCRIPTION
                           "Slot number relative to the containing card or 
                           chassis, or -1 if neither applicable nor 
                           determinable."
                   ::= { cardTableEntry 7 }

               cardContainedByIndex OBJECT-TYPE
                   SYNTAX  INTEGER
                   ACCESS  read-only
                   STATUS  deprecated
                   DESCRIPTION
                           "cardIndex of the parent card which
                           directly contains this card, or 0 if
                           contained by the chassis, or -1 if not
                           applicable nor determinable."
                   ::= { cardTableEntry 8 }

               cardOperStatus OBJECT-TYPE
                   SYNTAX  INTEGER {
                          not-specified(1), 
                          up(2),
                          down(3),
                          standby(4)
                      }
                   ACCESS  read-only
                   STATUS  deprecated
                   DESCRIPTION
                           "The operational status of the card.
                           cardOperStatus is up when a card is
                           recognized by the device and is enabled for
                           operation. cardOperStatus is down if the
                           card is not recognized by the device, or if
                           it is not enabled for operation.
                           cardOperStatus is standby if the card is
                           enabled and acting as a standby slave"
                   ::= { cardTableEntry 9 }

               cardSlots OBJECT-TYPE
                   SYNTAX  INTEGER
                   ACCESS  read-only
                   STATUS  deprecated
                   DESCRIPTION
                           "Number of slots on this card, or 0 if no
                           slots or not applicable, or -1 if not 
			   determinable."
                   ::= { cardTableEntry 10 }

               -- End of table


               chassisSlots OBJECT-TYPE
                   SYNTAX  INTEGER
                   ACCESS  read-only
                   STATUS  deprecated
                   DESCRIPTION
                           "Number of slots in this chassis, or -1 of
                           neither applicable nor determinable."
                   ::= { chassis 12 }

               cardIfIndexTable OBJECT-TYPE
                   SYNTAX  SEQUENCE OF CardIfIndexEntry
                   ACCESS  not-accessible
                   STATUS  deprecated
                   DESCRIPTION
                            "Chassis card table."
                   ::= { chassis 13 }

               cardIfIndexEntry OBJECT-TYPE
                   SYNTAX CardIfIndexEntry
                   ACCESS  not-accessible
                   STATUS  deprecated
                   DESCRIPTION
                            "Chassis card table."
                   INDEX { cardIfIndex }
               ::= { cardIfIndexTable 1 }

               CardIfIndexEntry ::=
                   SEQUENCE {
                       cardIfIndex
                           INTEGER,
                       cardIfSlotNumber
                           INTEGER,
                       cardIfPortNumber
                           INTEGER,
                       cardIfCardIndex
                           INTEGER,
                       cardIfConnectorTypeEnabled
                           INTEGER
                   }

               cardIfIndex OBJECT-TYPE
                   SYNTAX  INTEGER
                   ACCESS  read-only
                   STATUS  deprecated
                   DESCRIPTION
                           "matches RFC1213 ifTable IfIndex"
                   ::= { cardIfIndexEntry 1 }

               cardIfSlotNumber OBJECT-TYPE
                   SYNTAX  INTEGER
                   ACCESS  read-only
                   STATUS  deprecated
                   DESCRIPTION
                           "Chassis slot number, or -1 if neither
                           applicable nor determinable."
                   ::= { cardIfIndexEntry 2 }

               cardIfPortNumber OBJECT-TYPE
                   SYNTAX  INTEGER
                   ACCESS  read-only
                   STATUS  deprecated
                   DESCRIPTION
                           "Chassis port number, unique per port on a 
                            given card if available. If cardIfPortNumber is not
                            applicable to the card, then the object instance
                            won't be populated"
                   ::= { cardIfIndexEntry 3 }

               cardIfCardIndex OBJECT-TYPE
                   SYNTAX  INTEGER
                   ACCESS  read-only
                   STATUS  deprecated
                   DESCRIPTION
                           "cardIndex of the card in the Chassis 
                            cardTable which contains this interface, or -1 if
                            not applicable."
                   ::= { cardIfIndexEntry 4 }

               cardIfConnectorTypeEnabled OBJECT-TYPE
                   SYNTAX  INTEGER {
                           not-specified(1), 
                           none (2),
                           rj-45 (3),
                           db-40 (4),
                           db-15 (5),
                           auto-select (6),
                           gbic-sx (7),
                           gbic-lx (8),
                           gbic-lh (9),
                           gbic-cx (10),
                           gbic-zx (11),
                           missing (12),
                           mmf-st (13),
                           mmf-sc (14),
                           rj-11 (15),
                           rj-48s (16),
                           rj-48c (17),
                           db-60 (18),
                           gbic-stack(19),
                           gbic-1000baset(20)
                   }
                   ACCESS  read-only
                   STATUS  deprecated
                   DESCRIPTION
                           "Interface connector type currently
                           enabled. Value will be 1 if not known or not
                           used, or 2 if none of this ports' interface
                           connectors are enabled."
                   ::= { cardIfIndexEntry 5 }

	       -- End of table

               chassisPartner OBJECT-TYPE
                   SYNTAX  INTEGER {
			cisco(1)
			,synoptics(2)
			,chipcom(3)
			,cabletron(4)
			,dec(5)
			,ncr(6)
			,usrobotics(7)
			,alcatel(8)
			,nec(9)
			,dsc(10)
			,microcom(11)
			,oki(12)
			,ubn(13)
			,hp(14)
			,samsung(15)
			,mitsubishi(16)
                   }
                   ACCESS  read-only
                   STATUS  deprecated
                   DESCRIPTION
                           "Used to determine if this is a partner 
                            variant of a product."
                   ::= { chassis 14 }

               sysUpTimeAtLastChassisChange OBJECT-TYPE
                   SYNTAX  TimeTicks
                   ACCESS  read-only
                   STATUS  deprecated
                   DESCRIPTION
                           "Time in seconds/100 from the last cold
                           start to the last change in the chassis'
                           configuration. This value will be updated
                           whenever the chassis experiences a change
                           in the count, type, or slot position of
                           a card in cardTable."
                   ::= { chassis 15 }

--%DNP% not implemented (yet).
--%DNP%
--%DNP% TRAP DEFINITIONS
--%DNP%

               chassisTraps OBJECT IDENTIFIER		--%DNP%
                   ::= { chassis 16 }			--%DNP%

               chassisChangeTrap TRAP-TYPE		--%DNP%
                   ENTERPRISE { chassisTraps }		--%DNP%
                   VARIABLES {				--%DNP%
                             cardType,			--%DNP%
                             cardDescr,			--%DNP%
                             cardSerial			--%DNP%
                   }					--%DNP%
                   DESCRIPTION				--%DNP%
                           "This trap is issued when the value of	--%DNP%
                           sysUpTimeAtLastChassisChange has been	--%DNP%
                           updated due to the addition or removal of	--%DNP%
                           a card, which is identified by the variables."--%DNP%

                   ::= 1		--%DNP%


               END
