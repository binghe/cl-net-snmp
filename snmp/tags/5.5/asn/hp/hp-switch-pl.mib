-- HP ProLiant Switch MIBs
-- hpswitchpl
-- Version 0.0.2  05-19-2003
-- HISTORY
-- $Log: hp-switch-pl.mib,v $
-- Revision 1.4  2006/08/17 21:31:30  kallio
-- Mib update from Mgmt CD 7.60
--
-- Revision 1.3  2006/05/30 15:32:50  kallio
-- Mib with changes from Bruce G.
-- Revision submit_cheetah_19130/1 2006/03/22 10:46:55 vrincian
-- Lucian Badescu: fix for 6862  - "need unique sysObjectID for Angus" and
-- 6863 - "Need to update hpswitchpl.mib".
-- Add hpSwitchModuleBladetype3 and hpSwitchModuleBladetype4 seeds.
-- 
-- Revision submit_cheetah_10393/1 2005/01/05 21:01:49 mmacnt
-- code reorg - moved from lib/agent
-- 
-- Revision submit_cheetah_8619/1 2004/07/30 15:43:00 rrekha
-- Copy the hpswitchpl.mib from old /src/bert/lib/agent directory.
-- 
-- Revision submit_zoe_432/1 2003/06/11 00:54:09 smiao
-- Removed the strange characters.
-- 
-- Revision submit_zoe_370/1 2003/05/22 00:05:43 smiao
-- Updated to the new HP version for supporting SNMPv1 only.
-- 
-- Revision submit_zoe_181/1 2003/02/14 18:19:42 smiao
-- Creaed BERT MIB root file from HP.
-- $EndLog$
HP-SWITCH-PL-MIB    DEFINITIONS ::= BEGIN
    IMPORTS
        enterprises    FROM RFC1155-SMI;
    hp                                     OBJECT IDENTIFIER ::= { enterprises 11 }
    nm                                     OBJECT IDENTIFIER ::= { hp 2 }
    hpSystem                               OBJECT IDENTIFIER ::= { nm 3 }
    netElement                             OBJECT IDENTIFIER ::= { hpSystem 7 }
    hpEtherSwitch                          OBJECT IDENTIFIER ::= { netElement 11 }
    hpSwitchProliant                       OBJECT IDENTIFIER ::= { hpEtherSwitch 33 }

    hpSwitchModuleBladetype2               OBJECT IDENTIFIER ::= { hpSwitchProliant 1 }
    hpSwitchBladeType2-Products            OBJECT IDENTIFIER ::= { hpSwitchModuleBladetype2 1 }
    hpSwitchBladeType2-Mgmt                OBJECT IDENTIFIER ::= { hpSwitchModuleBladetype2 2 } 
--   SysObjId for p-GbE2 Interconnect Switch (1.3.6.1.4.1.11.2.3.7.11.33.1.1.1)
    hpProLiant-p-GbE2-InterconnectSwitch   OBJECT IDENTIFIER ::= { hpSwitchBladeType2-Products 1 } 
--   SysObjId for e-GbE2 Interconnect Switch (1.3.6.1.4.1.11.2.3.7.11.33.1.1.2) 
    hpProLiant-e-GbE2-InterconnectSwitch   OBJECT IDENTIFIER ::= { hpSwitchBladeType2-Products 2 }

    hpSwitchModuleBladetype3               OBJECT IDENTIFIER ::= { hpSwitchProliant 3 }
    hpSwitchBladeType3-Products            OBJECT IDENTIFIER ::= { hpSwitchModuleBladetype3 1 }
    hpSwitchBladeType3-Mgmt                OBJECT IDENTIFIER ::= { hpSwitchModuleBladetype3 2 }
--   SysObjId for CGESM  Interconnect Switch (1.3.6.1.4.1.11.2.3.7.11.33.3.1.1)
    hpProLiant-CGESM-InterconnectSwitch    OBJECT IDENTIFIER ::= { hpSwitchBladeType3-Products 1 } 

    hpSwitchModuleBladetype4               OBJECT IDENTIFIER ::= { hpSwitchProliant 4 }
    hpSwitchBladeType4-Products            OBJECT IDENTIFIER ::= { hpSwitchModuleBladetype4 1 } 
    hpSwitchBladeType4-Mgmt                OBJECT IDENTIFIER ::= { hpSwitchModuleBladetype4 2 }
--   SysObjId for GbE2c  Interconnect Switch (1.3.6.1.4.1.11.2.3.7.11.33.4.1.1)
    hpProLiant-GbE2c-InterconnectSwitch    OBJECT IDENTIFIER ::= { hpSwitchBladeType4-Products 1 }
END
