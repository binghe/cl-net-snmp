-- COPYRIGHT NOTICE
-- Copyright (c) Hewlett Packard Company, 2003
-- All rights reserved
-- 
-- HISTORY
-- $Log: bladetype4-physical.mib,v $
-- Revision 1.1  2006/08/17 21:34:53  kallio
-- New mibs from Mgmt CD 7.60
--
-- Revision 1.1  2006/05/30 15:17:33  kallio
-- Initial revision
-- Revision submit_cheetah_20427/1 2006/05/05 17:20:20 bradianu
-- File merge
-- 
-- Revision submit_cheetah_20375/1 2006/05/04 12:15:09 vrincian
-- stgNewCfgAgingTime - Remove for OSCAR_PROJECT.
-- 
-- Revision submit_cheetah_20194/1 2006/04/26 12:27:08 virgiliu
-- Merge aosFailover.mib_raw into this file.
-- 
-- Revision submit_cheetah_20001/1 2006/04/19 09:13:25 vrincian
-- Lucian Badescu: Change SNMP mib file title depending on project type.
-- Complete the support for Angus's private mibs beneath
-- hpSwitchModuleBladetype4-Mgmt OID.
-- 
-- Revision submit_cheetah_19958/1 2006/04/18 10:20:54 vrincian
-- Added leaf mstpDigest for digest of the mstp.
-- 
-- Revision submit_cheetah_19452/1 2006/03/30 14:23:23 drosu
-- Changed range of vlans that can be added to stg/cist.
-- 
-- Revision submit_cheetah_19447/1 2006/03/30 14:02:23 drosu
-- Added support for adding vlan to cist (mstp mode).
-- 
-- Revision submit_cheetah_19287/1 2006/03/24 12:15:02 virgiliu
-- ADD pmNewCfgPmonDelete to delete a monitor port.
-- 
-- Revision submit_cheetah_19130/1 2006/03/22 10:50:39 vrincian
-- Lucian Badescu: fix for 6862  - "need unique sysObjectID for Angus" and
-- 6863 - "Need to update hpswitchpl.mib".
-- Put all Angus private OIDs beneath hpSwitchModuleBladetype4-Mgmt.
-- 
-- Revision submit_cheetah_18021/1 2006/02/15 13:05:27 vrincian
-- Added defined for LACP features.
-- 
-- Revision submit_cheetah_17074/1 2006/01/10 15:01:53 vrincian
-- Lucian Badescu: fix BERT build. Use TRUNK_HASH flag, instead of TRUNK_THASH.
-- 
-- Revision submit_cheetah_17016/1 2006/01/10 00:12:56 bshao
-- Turned off FAST_UPLINK and TRUNK_HASH for Angus.
-- 
-- Revision submit_cheetah_16986/1 2006/01/05 23:51:42 bshao
-- Fixed compilation error when LACP, IEEE_8021X BCM569X_FILTERING
-- BERT_8021P is disabled.
-- 
-- Revision submit_cheetah_16895/1 2005/12/26 07:14:33 bshao
-- Added WEBUI and SNMP support for GVRP.
-- 
-- Revision submit_cheetah_16777/1 2005/12/20 13:24:17 vrincian
-- Lucian Badescu: Add/change some OIDs to complete SNMP support for
-- "/info/l2/cist" for Bert project.
-- 
-- Revision submit_cheetah_16735/1 2005/12/16 14:19:33 vrincian
-- Lucian Badescu: Add some OIDs to complete SNMP support for "/info/l2/stp".
-- 
-- Revision submit_cheetah_16704/1 2005/12/14 10:02:58 drosu
-- Added mib objects to support UFD stats table.
-- 
-- Revision submit_cheetah_16640/1 2005/12/12 13:08:06 drosu
-- Added LACP stats mib objects.
-- 
-- Revision submit_cheetah_16604/1 2005/12/09 15:21:02 vrincian
-- Lucian Badescu: Add SNMP support for "/info/l2/trunk" for BERT project.
-- 
-- Revision submit_cheetah_16556/1 2005/12/09 12:14:42 vrincian
-- Lucian Badescu: Add SNMP support for "/info/l2/vlan".
-- 
-- Revision submit_cheetah_16560/1 2005/12/08 16:44:21 bradianu
-- permit compiling with flag BERT_CFG_L2_FDB_STATIC undefined.
-- 
-- Revision submit_cheetah_16527/1 2005/12/08 09:18:00 vrincian
-- Lucian Badescu: add SNMP support for "/info/l2/gen".
-- 
-- Revision submit_cheetah_16411/1 2005/12/07 12:14:10 vrincian
-- Lucian Badescu: add SNMP support for /info/l2/8021p.
-- 
-- Revision submit_cheetah_15465/1 2005/10/25 14:38:35 coman
-- mstCistNewCfgBridgeHelloTime/mstCistNewCfgBridgeHelloTime objects removed for Bert
-- 
-- Revision submit_cheetah_15309/1 2005/10/19 11:04:06 drosu
-- added enable/disable 802.1x mib
-- 
-- Revision submit_cheetah_15191/1 2005/10/14 16:50:47 coman
-- Added SNMP support for static fdb configuration on Bert
-- 
-- Revision submit_cheetah_15184/1 2005/10/13 12:39:11 vrincian
-- Lucian Badescu: Add stgCurCfgPortFastFwd/stgNewCfgPortFastFwd SNMP objects 
-- to configure per port fast forwarding mode for Bert Sw.
-- Fix for Q01225520 - "SNMP -can not set port fast forwarding mode".
-- 
-- Revision submit_cheetah_15164/1 2005/10/12 17:01:13 coman
-- Added SNMP support for fdb info on Bert.
-- 
-- Revision submit_cheetah_15107/1 2005/10/12 13:00:23 drosu
-- Added some mibs for 802.1x
-- 
-- Revision submit_cheetah_13685/1 2005/08/11 19:09:05 rrekha
-- More cleanup of excludes from the Makefile. Moved them
-- to #if defines in the corresponding *.ctl_raw and *.mib_raw files.
-- 
-- Revision submit_cheetah_13551/1 2005/08/05 17:26:18 coman
-- UFD implementation ported from 2.2 stream
-- 
-- Revision submit_cheetah_12944/1 2005/07/02 13:13:05 coman
-- Added PORT_VLAN_MIRR flag for vlan mirroring mibs on Bert&Zoe
-- 
-- Revision submit_cheetah_12732/1 2005/06/20 22:23:21 thoang3
-- Remove the thashL3 object since this should never be used on BERT/ZOE as 
-- per Cynthia.
-- 
-- Revision submit_cheetah_11095/1 2005/03/03 02:53:44 tolin
-- Added trunk hash support for Bert mibs
-- 
-- Revision submit_cheetah_10393/1 2005/01/05 21:01:39 mmacnt
-- code reorg - moved from lib/agent
-- 
-- Revision submit_cheetah_10219/1 2004/11/16 18:46:14 dillibab
-- Added SNMP objects to configure STP Port Link Type and Edge State.
-- 
-- Revision submit_cheetah_10075/1 2004/11/04 18:53:29 bshao
-- CR 1016467: Changed CIST port priority in SNMP/BBI to
-- 0 - 240.
-- 
-- Revision submit_cheetah_9239/1 2004/09/08 00:44:59 rrekha
-- Cleanup L2 related flags.
-- 
-- Revision submit_cheetah_8623/1 2004/08/03 18:34:21 rrekha
-- Move qos configuration to a new mib bt2qos.mib.
-- 
-- Revision submit_cheetah_8578/1 2004/07/30 00:53:53 rrekha
-- Moved from /src/bert/lib/agent directory. 
-- Converted the MIBs to SMIv2.
-- 
-- Revision submit_cheetah_8419/1 2004/07/22 22:21:15 dtai
-- FAST_UPLINK: defined OIDs
-- 
-- Revision submit_cheetah_8296/1 2004/07/13 21:53:20 dleu
-- Added SNMP support for ELMO_TEAMING_TRUNK.
-- 
-- Revision submit_cheetah_7917/1 2004/06/23 22:19:37 kanil
-- Added new tree element qos8021p 
-- 
-- Revision submit_zoe_181/1 2003/02/14 18:17:53 smiao
-- Adjusted MIB nodes for HP MIB tree.
-- 
-- Revision submit_zoe_165/1 2003/02/04 23:05:41 smiao
-- Created MIB files for HP BERT project.
-- 
-- $EndLog$
--

BLADETYPE4-PHYSICAL-MIB DEFINITIONS ::= BEGIN

IMPORTS
    MODULE-IDENTITY, OBJECT-TYPE, Integer32, Counter32, Gauge32, TimeTicks
        FROM SNMPv2-SMI
    DisplayString, PhysAddress
        FROM SNMPv2-TC
    BridgeId
        FROM BRIDGE-MIB
    hpSwitchBladeType4-Mgmt
        FROM HP-SWITCH-PL-MIB;

layer2 MODULE-IDENTITY
    LAST-UPDATED "200312050000Z" --  5 December 2003
    ORGANIZATION "Hewlett Packard Company "
    CONTACT-INFO "customerservice@hp.com"
    DESCRIPTION
        "The MIB module for the Layer 2 configuration, statistics and 
         information ."
    ::= { hpSwitchBladeType4-Mgmt 2 }

layer2Configs     OBJECT IDENTIFIER ::= { layer2 1 }
layer2Stats       OBJECT IDENTIFIER ::= { layer2 2 }
layer2Info        OBJECT IDENTIFIER ::= { layer2 3 }
layer2Oper        OBJECT IDENTIFIER ::= { layer2 4 }

vlan              OBJECT IDENTIFIER ::= { layer2Configs 1 }
trunkgroup        OBJECT IDENTIFIER ::= { layer2Configs 2 }
stgCfg            OBJECT IDENTIFIER ::= { layer2Configs 3 }
mirroring         OBJECT IDENTIFIER ::= { layer2Configs 4 }
mstCfg            OBJECT IDENTIFIER ::= { layer2Configs 5 }
thash             OBJECT IDENTIFIER ::= { layer2Configs 7 }
l2GeneralCfg      OBJECT IDENTIFIER ::= { layer2Configs 8 }
ufd               OBJECT IDENTIFIER ::= { layer2Configs 9 }

-- layer2Configs 10 is being used by failoverCfg in aosFailoverCfg.mib

fdb               OBJECT IDENTIFIER ::= { layer2Configs 12 }

thashL2           OBJECT IDENTIFIER ::= { thash 1 }

mirrPortMirr      OBJECT IDENTIFIER ::= { mirroring 1 }

mstGeneralCfg     OBJECT IDENTIFIER ::= { mstCfg 1 }
mstCistCfg        OBJECT IDENTIFIER ::= { mstCfg 2 }

ufdGeneralCfg     OBJECT IDENTIFIER ::= { ufd 1 }
fdbGeneralCfg	  OBJECT IDENTIFIER ::= { fdb 1 }


fdbStats	  OBJECT IDENTIFIER ::= { layer2Stats 1 }
stpStats	  OBJECT IDENTIFIER ::= { layer2Stats 2 }
ufdStats          OBJECT IDENTIFIER ::= { layer2Stats 4 }

cistInfo          OBJECT IDENTIFIER ::= { layer2Info 1 }
fdbInfo           OBJECT IDENTIFIER ::= { layer2Info 2 }
stpInfo           OBJECT IDENTIFIER ::= { layer2Info 3 }
genInfo           OBJECT IDENTIFIER ::= { layer2Info 7 }
vlanInfo          OBJECT IDENTIFIER ::= { layer2Info 8 }
trunkGroupInfo    OBJECT IDENTIFIER ::= { layer2Info 9 }


cistGeneralInfo   OBJECT IDENTIFIER ::= { cistInfo 1 }

-- VLAN group
vlanMaxEnt OBJECT-TYPE
    SYNTAX  Integer32 
    MAX-ACCESS  read-only
    STATUS  current
    DESCRIPTION
        "The maximum number of rows in the VLAN configuration table."
    ::= { vlan 1 }

vlanCurCfgTable OBJECT-TYPE
    SYNTAX  SEQUENCE OF VlanCurCfgTableEntry
    MAX-ACCESS  not-accessible
    STATUS  current
    DESCRIPTION
        "The table of VLAN configuration."
    ::= { vlan 2 }

vlanCurCfgTableEntry OBJECT-TYPE
    SYNTAX  VlanCurCfgTableEntry
    MAX-ACCESS  not-accessible
    STATUS  current
    DESCRIPTION
        "A row in the VLAN configuration table."
    INDEX  { vlanCurCfgVlanId }
    ::= { vlanCurCfgTable 1 }

VlanCurCfgTableEntry ::= SEQUENCE {
    vlanCurCfgVlanId 		Integer32,
    vlanCurCfgVlanName 		DisplayString,
    vlanCurCfgPorts 		OCTET STRING,
    vlanCurCfgState 		INTEGER,
    vlanCurCfgStg  	        Integer32
    }

vlanCurCfgVlanId OBJECT-TYPE
    SYNTAX  Integer32
    MAX-ACCESS  read-only
    STATUS  current
    DESCRIPTION
        "The VLAN identifier."
    ::= { vlanCurCfgTableEntry 1 }

vlanCurCfgVlanName OBJECT-TYPE
    SYNTAX  DisplayString (SIZE(0..32))
    MAX-ACCESS  read-only
    STATUS  current
    DESCRIPTION
        "The VLAN name."
    ::= { vlanCurCfgTableEntry 2 }

vlanCurCfgPorts	OBJECT-TYPE
    SYNTAX  OCTET STRING
    MAX-ACCESS  read-only
    STATUS  current
    DESCRIPTION
        "The port list in the VLAN. The ports are presented in bitmap format.
	 in receiving order:

	     OCTET 1  OCTET 2  .....
             xxxxxxxx xxxxxxxx ..... 
             ||    || |_ port 8
             ||    ||  
             ||    ||___ port 7
             ||    |____ port 6
             ||      .    .   .
             ||_________ port 1
             |__________ reserved

         where x : 1 - The represented port belongs to the VLAN
		   0 - The represented port does not belong to the VLAN"
    ::= { vlanCurCfgTableEntry 3 }

vlanCurCfgState	OBJECT-TYPE
    SYNTAX  INTEGER  {
	enabled(2),
	disabled(3)
	}
    MAX-ACCESS  read-only
    STATUS  current
    DESCRIPTION
        "Enable or disable a VLAN"
    ::= { vlanCurCfgTableEntry 4 }


vlanCurCfgStg OBJECT-TYPE
    SYNTAX  Integer32  
    MAX-ACCESS  read-only
    STATUS  current
    DESCRIPTION
        "The Spanning Tree Group for the VLAN."
    ::= { vlanCurCfgTableEntry 6 }

vlanNewCfgTable OBJECT-TYPE
    SYNTAX  SEQUENCE OF VlanNewCfgTableEntry
    MAX-ACCESS  not-accessible
    STATUS  current
    DESCRIPTION
        "The table of VLAN configuration."
    ::= { vlan 3 }

vlanNewCfgTableEntry OBJECT-TYPE
    SYNTAX  VlanNewCfgTableEntry
    MAX-ACCESS  not-accessible
    STATUS  current
    DESCRIPTION
        "A row in the VLAN configuration table."
    INDEX  { vlanNewCfgVlanId }
    ::= { vlanNewCfgTable 1 }

VlanNewCfgTableEntry ::= SEQUENCE {
    vlanNewCfgVlanId 		Integer32,
    vlanNewCfgVlanName 		DisplayString,
    vlanNewCfgPorts 		OCTET STRING,
    vlanNewCfgState 		INTEGER,
    vlanNewCfgAddPort 		Integer32,
    vlanNewCfgRemovePort	Integer32,
    vlanNewCfgDelete 		INTEGER,
    vlanNewCfgStg  	        Integer32
    }

vlanNewCfgVlanId OBJECT-TYPE
    SYNTAX  Integer32
    MAX-ACCESS  read-only
    STATUS  current
    DESCRIPTION
        "The VLAN identifier."
    ::= { vlanNewCfgTableEntry 1 }

vlanNewCfgVlanName OBJECT-TYPE
    SYNTAX  DisplayString (SIZE(0..32))
    MAX-ACCESS  read-create
    STATUS  current
    DESCRIPTION
        "The VLAN name."
    ::= { vlanNewCfgTableEntry 2 }

vlanNewCfgPorts	OBJECT-TYPE
    SYNTAX  OCTET STRING
    MAX-ACCESS  read-only
    STATUS  current
    DESCRIPTION
        "The port list in the VLAN.  The ports are presented in bitmap format.
         in receiving order:

	     OCTET 1  OCTET 2  .....
             xxxxxxxx xxxxxxxx ..... 
             ||    || |_ port 8
             ||    ||  
             ||    ||___ port 7
             ||    |____ port 6
             ||      .    .   .
             ||_________ port 1
             |__________ reserved

         where x : 1 - The represented port belongs to the VLAN
	           0 - The represented port does not belong to the VLAN"
    ::= { vlanNewCfgTableEntry 3 }

vlanNewCfgState	OBJECT-TYPE
    SYNTAX  INTEGER  {
	enabled(2),
	disabled(3)
	}
    MAX-ACCESS  read-create
    STATUS  current
    DESCRIPTION
        "Enable or disable a VLAN"
    ::= { vlanNewCfgTableEntry 4 }

vlanNewCfgAddPort OBJECT-TYPE
    SYNTAX  Integer32
    MAX-ACCESS  read-create
    STATUS  current
    DESCRIPTION
        "The port to be added to the specified VLAN.  A '0' value is 
         returned when read."
    ::= { vlanNewCfgTableEntry 5 }

vlanNewCfgRemovePort OBJECT-TYPE
    SYNTAX  Integer32
    MAX-ACCESS  read-create
    STATUS  current
    DESCRIPTION
        "The port to be removed from the specified VLAN.  A '0'
         value is returned when read."
    ::= { vlanNewCfgTableEntry 6 }

vlanNewCfgDelete OBJECT-TYPE
    SYNTAX  INTEGER  {
        other(1),
        delete(2)
        }
    MAX-ACCESS  read-create
    STATUS  current
    DESCRIPTION
        "This is an action object to create or delete a VLAN.
         other(1) is returned always when read.
         The following values are writable: delete(2)...to delete a VLAN"
    ::= { vlanNewCfgTableEntry 7 }


vlanNewCfgStg OBJECT-TYPE
    SYNTAX  Integer32  
    MAX-ACCESS  read-create
    STATUS  current
    DESCRIPTION
        "The Spanning Tree Group for the VLAN."
    ::= { vlanNewCfgTableEntry 9 }

-- Trunk Group Group
trunkGroupTableMaxSize OBJECT-TYPE
    SYNTAX  Integer32
    MAX-ACCESS  read-only
    STATUS  current
    DESCRIPTION
        "The maximum number of entries in trunk group table."
    ::= { trunkgroup 1 }

trunkGroupCurCfgTable OBJECT-TYPE
    SYNTAX  SEQUENCE OF TrunkGroupCurCfgTableEntry
    MAX-ACCESS  not-accessible
    STATUS  current
    DESCRIPTION
        "The table of trunk group configuration."
    ::= { trunkgroup 2 }

trunkGroupCurCfgTableEntry OBJECT-TYPE
    SYNTAX  TrunkGroupCurCfgTableEntry
    MAX-ACCESS  not-accessible
    STATUS  current
    DESCRIPTION
        "A row in the trunk group configuration table."
    INDEX   { trunkGroupCurCfgIndex }
    ::= { trunkGroupCurCfgTable 1 }

TrunkGroupCurCfgTableEntry ::= SEQUENCE {
    trunkGroupCurCfgIndex         Integer32,
    trunkGroupCurCfgPorts         OCTET STRING,
    trunkGroupCurCfgState         INTEGER
    }
 
trunkGroupCurCfgIndex OBJECT-TYPE
    SYNTAX  Integer32  
    MAX-ACCESS  read-only
    STATUS  current
    DESCRIPTION
        "The identifier of the trunk group."
    ::= { trunkGroupCurCfgTableEntry 1 }
 
trunkGroupCurCfgPorts OBJECT-TYPE
    SYNTAX  OCTET STRING
    MAX-ACCESS  read-only
    STATUS  current
    DESCRIPTION
        "The port list in the trunk group. The ports are presented in 
         bitmap format.
 
         in receiving order:
 
             OCTET 1  OCTET 2  .....
             xxxxxxxx xxxxxxxx ..... 
             ||    || |_ port 8
             ||    ||  
             ||    ||___ port 7
             ||    |____ port 6
             ||      .    .   .
             ||_________ port 1
             |__________ reserved

         where x : 1 - The represented port belongs to the trunk group
                   0 - The represented port does not belong to the trunk group"
    ::= { trunkGroupCurCfgTableEntry 2 }
 
trunkGroupCurCfgState OBJECT-TYPE
    SYNTAX  INTEGER  {
        enable(1),
        disable(2)
        }
    MAX-ACCESS  read-only
    STATUS  current
    DESCRIPTION
        "Enable or disable a trunk group."
    ::= { trunkGroupCurCfgTableEntry 3 }
 
 
trunkGroupNewCfgTable OBJECT-TYPE
    SYNTAX  SEQUENCE OF TrunkGroupNewCfgTableEntry
    MAX-ACCESS  not-accessible
    STATUS  current
    DESCRIPTION
        "The table of trunk group configuration."
    ::= { trunkgroup 3 }

trunkGroupNewCfgTableEntry OBJECT-TYPE
    SYNTAX  TrunkGroupNewCfgTableEntry
    MAX-ACCESS  not-accessible
    STATUS  current
    DESCRIPTION
        "A row in the trunk group configuration table."
    INDEX   { trunkGroupNewCfgIndex }
    ::= { trunkGroupNewCfgTable 1 }

TrunkGroupNewCfgTableEntry ::= SEQUENCE {
    trunkGroupNewCfgIndex          Integer32,
    trunkGroupNewCfgPorts          OCTET STRING,
    trunkGroupNewCfgAddPort        Integer32,
    trunkGroupNewCfgRemovePort     Integer32,
    trunkGroupNewCfgState          INTEGER,
    trunkGroupNewCfgDelete         INTEGER
    }
 
trunkGroupNewCfgIndex OBJECT-TYPE
    SYNTAX  Integer32  
    MAX-ACCESS  read-only
    STATUS  current
    DESCRIPTION
        "The identifier of the trunk group."
    ::= { trunkGroupNewCfgTableEntry 1 }
 
trunkGroupNewCfgPorts OBJECT-TYPE
    SYNTAX  OCTET STRING
    MAX-ACCESS  read-only
    STATUS  current
    DESCRIPTION
        "The port list in the trunk group.  The ports are presented
         in bitmap format.

         in receiving order:

             OCTET 1  OCTET 2  .....
             xxxxxxxx xxxxxxxx ..... 
             ||    || |_ port 8
             ||    ||  
             ||    ||___ port 7
             ||    |____ port 6
             ||      .    .   .
             ||_________ port 1
             |__________ reserved
 
         where x : 1 - The represented port belongs to the trunk group
                   0 - The represented port does not belong to the trunk group"
    ::= { trunkGroupNewCfgTableEntry 2 }
 
trunkGroupNewCfgAddPort OBJECT-TYPE
    SYNTAX  Integer32
    MAX-ACCESS  read-create
    STATUS  current
    DESCRIPTION
        "The port to be added in the trunk group. When read, 0 is returned."
    ::= { trunkGroupNewCfgTableEntry 3 }

trunkGroupNewCfgRemovePort OBJECT-TYPE
    SYNTAX  Integer32
    MAX-ACCESS  read-create
    STATUS  current
    DESCRIPTION
        "The port to be deleted from the trunk group. when read, 0
	 is returned."
    ::= { trunkGroupNewCfgTableEntry 4 }

trunkGroupNewCfgState OBJECT-TYPE
    SYNTAX  INTEGER  {
        enable(1),
        disable(2)
        }
    MAX-ACCESS  read-create
    STATUS  current
    DESCRIPTION
        "Enable or disable a trunk group."
    ::= { trunkGroupNewCfgTableEntry 5 }
 
trunkGroupNewCfgDelete OBJECT-TYPE
    SYNTAX  INTEGER  {
        other(1),
        delete(2)
        }
    MAX-ACCESS  read-create
    STATUS  current
    DESCRIPTION
        "Setting the value to delete(2) will delete the entire
         row. When read, other(1) is returned."
    ::= { trunkGroupNewCfgTableEntry 6 }




-- Spanning Tree Group Configuration
-- This group specifies the additional configurations that are not
-- covered by the Bridge MIB (RFC 1493).
-- The relative Spanning Tree information can be retrieved or configured
-- using Bridge MIB with an unique community string for each group specified
-- in entLogicalTable of Entity MIB (RFC 2037).
--
stgCurCfgTable OBJECT-TYPE
    SYNTAX SEQUENCE OF StgCurCfgTableEntry
    MAX-ACCESS not-accessible
    STATUS current
    DESCRIPTION
        "The table of Spanning Tree Group configuration."
    ::= { stgCfg 1 }

stgCurCfgTableEntry OBJECT-TYPE
    SYNTAX StgCurCfgTableEntry
    MAX-ACCESS not-accessible
    STATUS current
    DESCRIPTION
        "Information about a particular Spanning Tree Group configuration."
    INDEX { stgCurCfgIndex }
    ::= { stgCurCfgTable 1 }

StgCurCfgTableEntry ::= SEQUENCE {
    stgCurCfgIndex           Integer32,
    stgCurCfgState           INTEGER,
    stgCurCfgVlanBmap1	     OCTET STRING,	-- obsolete
    stgCurCfgVlanBmap2	     OCTET STRING,      -- obsolete
    stgCurCfgPriority        INTEGER,
    stgCurCfgBrgHelloTime    INTEGER,
    stgCurCfgBrgForwardDelay INTEGER,
    stgCurCfgBrgMaxAge       INTEGER,
    stgCurCfgAgingTime       INTEGER,
    stgCurCfgVlanBmap        OCTET STRING
    }

stgCurCfgIndex OBJECT-TYPE
    SYNTAX Integer32
    MAX-ACCESS read-only
    STATUS current
    DESCRIPTION
        "The identifier of a particular Spanning Tree Group.  This is also
         index to the entLogicalTable of Entity MIB."
    ::= { stgCurCfgTableEntry 1 }

stgCurCfgState OBJECT-TYPE
    SYNTAX INTEGER {
        on(1),
        off(2)
        }
    MAX-ACCESS read-only
    STATUS current
    DESCRIPTION
        "Turn on of off Spanning Tree operation of a particular Spanning
         Tree Group."
    ::= { stgCurCfgTableEntry 2 }

stgCurCfgVlanBmap1 OBJECT-TYPE
    SYNTAX  OCTET STRING (SIZE(0..256)) 
    MAX-ACCESS  read-only
    STATUS  obsolete
    DESCRIPTION
	"The vlans applied to the spanning tree group.  The vlans are 
         presented in bitmap format. This string displays vlan number
	 from 1 to 2048.

	 in receiving order:

	     OCTET 1  OCTET 2  .....
             xxxxxxxx xxxxxxxx ..... 
             ||    || |_ vlan 9
             ||    ||  
             ||    ||___ vlan 8
             ||    |____ vlan 7
             ||      .    .   .
             ||_________ vlan 2
             |__________ vlan 1 (as index to stgCurCfgTable)

         where x : 1 - The represented vlan applied to the spanning tree. 
		   0 - The represented vlan not applied to the spanning tree"
    ::= { stgCurCfgTableEntry 3 }

stgCurCfgVlanBmap2 OBJECT-TYPE
    SYNTAX  OCTET STRING (SIZE(0..256)) 
    MAX-ACCESS  read-only
    STATUS  obsolete
    DESCRIPTION
	"The vlans applied to the spanning tree group.  The vlans are 
         presented in bitmap format. This string displays vlan number
	 from 2049 to 4096.

	 in receiving order:

	     OCTET 1  OCTET 2  .....
             xxxxxxxx xxxxxxxx ..... 
             ||    || |_ vlan 2057 
             ||    ||  
             ||    ||___ vlan 2056 
             ||    |____ vlan 2055 
             ||      .    .   .
             ||_________ vlan 2050 
             |__________ vlan 2049 (as index to stgCurCfgTable)

         where x : 1 - The represented vlan applied to the spanning tree. 
		   0 - The represented vlan not applied to the spanning tree"
    ::= { stgCurCfgTableEntry 4 }

stgCurCfgPriority OBJECT-TYPE
    SYNTAX  INTEGER (0..65535)
    MAX-ACCESS  read-only
    STATUS  current
    DESCRIPTION
        "The value of the write-able portion of the Bridge ID, i.e., the first
         two octets of the (8 octet long) Bridge ID."
    ::= { stgCurCfgTableEntry 5 }

stgCurCfgBrgHelloTime OBJECT-TYPE
    SYNTAX  INTEGER (1..10)
    MAX-ACCESS  read-only
    STATUS  current
    DESCRIPTION
        "The value in seconds that all bridges use for HelloTime when this 
         bridge is acting as the root."
    ::= { stgCurCfgTableEntry 6 }

stgCurCfgBrgForwardDelay OBJECT-TYPE
    SYNTAX  INTEGER (4..30)
    MAX-ACCESS  read-only
    STATUS  current
    DESCRIPTION
        "The value in seconds that all bridges use for ForwardDelay when this 
         bridge is acting as the root."
    ::= { stgCurCfgTableEntry 7 }

stgCurCfgBrgMaxAge OBJECT-TYPE
    SYNTAX  INTEGER (6..40)
    MAX-ACCESS  read-only
    STATUS  current
    DESCRIPTION
        "The value in seconds that all bridges use for MaxAge when this bridge
         is acting as the root."
    ::= { stgCurCfgTableEntry 8 }

stgCurCfgAgingTime OBJECT-TYPE
    SYNTAX  INTEGER (0..65535)
    MAX-ACCESS  read-only
    STATUS  current
    DESCRIPTION
        "The timeout period in seconds for aging out dynamically learned 
         forwarding information."
    ::= { stgCurCfgTableEntry 9 }

stgCurCfgVlanBmap OBJECT-TYPE
    SYNTAX  OCTET STRING (SIZE(0..512)) 
    MAX-ACCESS  read-only
    STATUS  current
    DESCRIPTION
	"The vlans applied to the spanning tree group.  The vlans are 
         presented in bitmap format. This string displays vlan number
	 from 1 to 4095.

	 in receiving order:

	     OCTET 1  OCTET 2  .....
             xxxxxxxx xxxxxxxx ..... 
             ||    || |_ vlan 9
             ||    ||  
             ||    ||___ vlan 8
             ||    |____ vlan 7
             ||      .    .   .
             ||_________ vlan 2
             |__________ vlan 1 (as index to stgCurCfgTable)

         where x : 1 - The represented vlan applied to the spanning tree. 
		   0 - The represented vlan not applied to the spanning tree"
    ::= { stgCurCfgTableEntry 10 }


stgNewCfgTable OBJECT-TYPE
    SYNTAX SEQUENCE OF StgNewCfgTableEntry
    MAX-ACCESS not-accessible
    STATUS current
    DESCRIPTION
        "The table of Spanning Tree Groups configuration in the new_config."
    ::= { stgCfg 2 }

stgNewCfgTableEntry OBJECT-TYPE
    SYNTAX StgNewCfgTableEntry
    MAX-ACCESS not-accessible
    STATUS current
    DESCRIPTION
        "Information about a particular Spanning Tree Group configuration."
    INDEX { stgNewCfgIndex }
    ::= { stgNewCfgTable 1 }

StgNewCfgTableEntry ::= SEQUENCE {
    stgNewCfgIndex           Integer32,
    stgNewCfgState           INTEGER,
    stgNewCfgDefaultCfg      INTEGER,
    stgNewCfgAddVlan         Integer32,
    stgNewCfgRemoveVlan      Integer32,
    stgNewCfgVlanBmap1	     OCTET STRING,      -- obsolete
    stgNewCfgVlanBmap2	     OCTET STRING,      -- obsolete
    stgNewCfgPriority        INTEGER,
    stgNewCfgBrgHelloTime    INTEGER,
    stgNewCfgBrgForwardDelay INTEGER,
    stgNewCfgBrgMaxAge       INTEGER,
    stgNewCfgVlanBmap        OCTET STRING
    }

stgNewCfgIndex  OBJECT-TYPE
    SYNTAX Integer32
    MAX-ACCESS read-only
    STATUS current
    DESCRIPTION
        "The identifier of a particular Spanning Tree Group.  This is also
         index to the entLogicalTable of Entity MIB."
    ::= { stgNewCfgTableEntry 1 }

stgNewCfgState OBJECT-TYPE
    SYNTAX INTEGER {
        on(1),
        off(2)
        }
    MAX-ACCESS read-create
    STATUS current
    DESCRIPTION
        "Turn on of off Spanning Tree operation of a particular Spanning
         Tree Group."
    ::= { stgNewCfgTableEntry 2 }

stgNewCfgDefaultCfg OBJECT-TYPE
    SYNTAX INTEGER {
        default-config(1)
        }
    MAX-ACCESS read-create
    STATUS current
    DESCRIPTION
        "Setting the value to default-config(1) will set the default
         configuration as recommended by IEEE 802.1D for a particular
         Spanning Tree Group.  default-config (1) is always returned 
	 When read, but it does not mean anything."
    ::= { stgNewCfgTableEntry 3 }

stgNewCfgAddVlan OBJECT-TYPE
    SYNTAX  Integer32
    MAX-ACCESS  read-create
    STATUS  current
    DESCRIPTION
        "The vlan to be added to the specified Spanning Tree Group.  A 
         '0' value is returned when read." 
    ::= {stgNewCfgTableEntry 4 }

stgNewCfgRemoveVlan OBJECT-TYPE
    SYNTAX  Integer32
    MAX-ACCESS  read-create
    STATUS  current
    DESCRIPTION
        "The vlan to be removed from the specified Spanning Tree Group.
         A '0' value is returned when read."
    ::= { stgNewCfgTableEntry 5 }

stgNewCfgVlanBmap1 OBJECT-TYPE
    SYNTAX  OCTET STRING (SIZE(0..256)) 
    MAX-ACCESS  read-only
    STATUS  obsolete
    DESCRIPTION
	"The vlans applied to the spanning tree group.  The vlans are 
         presented in bitmap format. This string displays vlan number
	 from 1 to 2048.

	 in receiving order:

	     OCTET 1  OCTET 2  .....
             xxxxxxxx xxxxxxxx ..... 
             ||    || |_ vlan 9
             ||    ||  
             ||    ||___ vlan 8
             ||    |____ vlan 7
             ||      .    .   .
             ||_________ vlan 2
             |__________ vlan 1 (as index to stgCurCfgTable)

         where x : 1 - The represented vlan applied to the spanning tree. 
		   0 - The represented vlan not applied to the spanning tree"
    ::= { stgNewCfgTableEntry 6 }

stgNewCfgVlanBmap2 OBJECT-TYPE
    SYNTAX  OCTET STRING (SIZE(0..256)) 
    MAX-ACCESS  read-only
    STATUS  obsolete
    DESCRIPTION
	"The vlans applied to the spanning tree group.  The vlans are 
         presented in bitmap format. This string displays vlan number
	 from 2049 to 4096.

	 in receiving order:

	     OCTET 1  OCTET 2  .....
             xxxxxxxx xxxxxxxx ..... 
             ||    || |_ vlan 2057 
             ||    ||  
             ||    ||___ vlan 2056 
             ||    |____ vlan 2055 
             ||      .    .   .
             ||_________ vlan 2050 
             |__________ vlan 2049 (as index to stgCurCfgTable)

         where x : 1 - The represented vlan applied to the spanning tree. 
		   0 - The represented vlan not applied to the spanning tree"
    ::= { stgNewCfgTableEntry 7 }

stgNewCfgPriority OBJECT-TYPE
    SYNTAX  INTEGER (0..65535)
    MAX-ACCESS  read-create
    STATUS  current
    DESCRIPTION
        "The value of the write-able portion of the Bridge ID, i.e., the first
         two octets of the (8 octet long) Bridge ID."
    ::= { stgNewCfgTableEntry 8 }

stgNewCfgBrgHelloTime OBJECT-TYPE
    SYNTAX  INTEGER (1..10)
    MAX-ACCESS  read-create
    STATUS  current
    DESCRIPTION
        "The value in seconds that all bridges use for HelloTime when this 
         bridge is acting as the root."
    ::= { stgNewCfgTableEntry 9 }

stgNewCfgBrgForwardDelay OBJECT-TYPE
    SYNTAX  INTEGER (4..30)
    MAX-ACCESS  read-create
    STATUS  current
    DESCRIPTION
        "The value in seconds that all bridges use for ForwardDelay when this 
         bridge is acting as the root."
    ::= { stgNewCfgTableEntry 10 }

stgNewCfgBrgMaxAge OBJECT-TYPE
    SYNTAX  INTEGER (6..40)
    MAX-ACCESS  read-create
    STATUS  current
    DESCRIPTION
        "The value in seconds that all bridges use for MaxAge when this bridge
         is acting as the root."
    ::= { stgNewCfgTableEntry 11 }

stgNewCfgVlanBmap OBJECT-TYPE
    SYNTAX  OCTET STRING (SIZE(0..512)) 
    MAX-ACCESS  read-only
    STATUS  current
    DESCRIPTION
	"The vlans applied to the spanning tree group.  The vlans are 
         presented in bitmap format. This string displays vlan number
	 from 1 to 4095.

	 in receiving order:

	     OCTET 1  OCTET 2  .....
             xxxxxxxx xxxxxxxx ..... 
             ||    || |_ vlan 9
             ||    ||  
             ||    ||___ vlan 8
             ||    |____ vlan 7
             ||      .    .   .
             ||_________ vlan 2
             |__________ vlan 1 (as index to stgCurCfgTable)

         where x : 1 - The represented vlan applied to the spanning tree. 
		   0 - The represented vlan not applied to the spanning tree"
    ::= { stgNewCfgTableEntry 13 }


stgCurCfgPortTable OBJECT-TYPE
    SYNTAX SEQUENCE OF StgCurCfgPortTableEntry
    MAX-ACCESS not-accessible
    STATUS current
    DESCRIPTION
        "The table of Spanning Tree Group port configuration in the
         current_config."
    ::= { stgCfg 3 }

stgCurCfgPortTableEntry OBJECT-TYPE
    SYNTAX StgCurCfgPortTableEntry
    MAX-ACCESS not-accessible
    STATUS current
    DESCRIPTION
        "Information about port configuration of a particular Spanning Tree
         Group."
    INDEX { stgCurCfgStgIndex, stgCurCfgPortIndex }
    ::= { stgCurCfgPortTable 1 }

StgCurCfgPortTableEntry ::= SEQUENCE {
    stgCurCfgStgIndex      Integer32,
    stgCurCfgPortIndex     Integer32,
    stgCurCfgPortState     INTEGER,
    stgCurCfgPortPriority  INTEGER,
    stgCurCfgPortPathCost  INTEGER,
    stgCurCfgPortLink      INTEGER,
    stgCurCfgPortEdge      INTEGER,
    stgCurCfgPortFastFwd   INTEGER
    }

stgCurCfgStgIndex OBJECT-TYPE
    SYNTAX Integer32
    MAX-ACCESS read-only
    STATUS current
    DESCRIPTION
        "The identifier of a particular Spanning Tree Group.  This is also
         index to the entLogicalTable of Entity MIB."
    ::= { stgCurCfgPortTableEntry 1 }

stgCurCfgPortIndex OBJECT-TYPE
    SYNTAX Integer32
    MAX-ACCESS read-only
    STATUS current
    DESCRIPTION
        "The port identifier of a particular Spanning Tree Group."
    ::= { stgCurCfgPortTableEntry 2 }

stgCurCfgPortState OBJECT-TYPE
    SYNTAX INTEGER {
        on(1),
        off(2)
        }
    MAX-ACCESS read-only
    STATUS current
    DESCRIPTION
        "Turn on of off Spanning Tree operation of a particular port of a
         Spanning Tree Group."
    ::= { stgCurCfgPortTableEntry 3 }

stgCurCfgPortPriority OBJECT-TYPE
    SYNTAX INTEGER (0..255)
    MAX-ACCESS read-only
    STATUS current
    DESCRIPTION
        "The value of the priority field which is contained in the first 
         (in network byte order) octet of the (2 octet long) Port ID."
    ::= { stgCurCfgPortTableEntry 4 }

stgCurCfgPortPathCost OBJECT-TYPE
    SYNTAX INTEGER (0..65535)
    MAX-ACCESS read-only
    STATUS current
    DESCRIPTION
       "The contribution of this port to the path cost of paths towards the 
        spanning tree root which include this port."
    ::= { stgCurCfgPortTableEntry 5 }

stgCurCfgPortLink OBJECT-TYPE
    SYNTAX INTEGER {
        auto(1),
        p2p(2),
        shared(3)
        }
    MAX-ACCESS read-only
    STATUS current
    DESCRIPTION
        "The type of the port link."
    ::= { stgCurCfgPortTableEntry 6 }

stgCurCfgPortEdge OBJECT-TYPE
    SYNTAX INTEGER {
        enabled(1),
        disabled(2)
        }
    MAX-ACCESS read-only
    STATUS current
    DESCRIPTION
        "The state of port edge."
    ::= { stgCurCfgPortTableEntry 7 }

stgCurCfgPortFastFwd OBJECT-TYPE
    SYNTAX INTEGER {
        enabled(1),
        disabled(2)
        }
    MAX-ACCESS read-only
    STATUS current
    DESCRIPTION
        "The state of port fast forwarding."
    ::= { stgCurCfgPortTableEntry 8 }

stgNewCfgPortTable OBJECT-TYPE
    SYNTAX SEQUENCE OF StgNewCfgPortTableEntry
    MAX-ACCESS not-accessible
    STATUS current
    DESCRIPTION
        "The table of Spanning Tree Group port configuration in the
         new_config."
    ::= { stgCfg 4 }

stgNewCfgPortTableEntry OBJECT-TYPE
    SYNTAX StgNewCfgPortTableEntry
    MAX-ACCESS not-accessible
    STATUS current
    DESCRIPTION
        "Information about port configuration of a particular Spanning Tree
         Group."
    INDEX { stgNewCfgStgIndex, stgNewCfgPortIndex }
    ::= { stgNewCfgPortTable 1 }

StgNewCfgPortTableEntry ::= SEQUENCE {
    stgNewCfgStgIndex      Integer32,
    stgNewCfgPortIndex     Integer32,
    stgNewCfgPortState     INTEGER,
    stgNewCfgPortPriority  INTEGER,
    stgNewCfgPortPathCost  INTEGER,
    stgNewCfgPortLink      INTEGER,
    stgNewCfgPortEdge      INTEGER,
    stgNewCfgPortFastFwd   INTEGER
    }

stgNewCfgStgIndex OBJECT-TYPE
    SYNTAX Integer32
    MAX-ACCESS read-only
    STATUS current
    DESCRIPTION
        "The identifier of a particular Spanning Tree Group.  This is also
         index to the entLogicalTable of Entity MIB."
    ::= { stgNewCfgPortTableEntry 1 }

stgNewCfgPortIndex OBJECT-TYPE
    SYNTAX Integer32
    MAX-ACCESS read-only
    STATUS current
    DESCRIPTION
        "The port identifier of a particular Spanning Tree Group."
    ::= { stgNewCfgPortTableEntry 2 }

stgNewCfgPortState OBJECT-TYPE
    SYNTAX INTEGER {
        on(1),
        off(2)
        }
    MAX-ACCESS read-create
    STATUS current
    DESCRIPTION
        "Turn on of off Spanning Tree operation of a particular port of a
         Spanning Tree Group."
    ::= { stgNewCfgPortTableEntry 3 }

stgNewCfgPortPriority OBJECT-TYPE
    SYNTAX INTEGER (0..255)
    MAX-ACCESS read-create
    STATUS current
    DESCRIPTION
        "The value of the priority field which is contained in the first 
         (in network byte order) octet of the (2 octet long) Port ID."
    ::= { stgNewCfgPortTableEntry 4 }

stgNewCfgPortPathCost OBJECT-TYPE
    SYNTAX INTEGER (0..65535)
    MAX-ACCESS read-create
    STATUS current
    DESCRIPTION
       "The contribution of this port to the path cost of paths towards the 
        spanning tree root which include this port."
    ::= { stgNewCfgPortTableEntry 5 }

stgNewCfgPortLink OBJECT-TYPE
    SYNTAX INTEGER {
        auto(1),
        p2p(2),
        shared(3)
        }
    MAX-ACCESS read-create
    STATUS current
    DESCRIPTION
        "The type of the port link."
    ::= { stgNewCfgPortTableEntry 6 }

stgNewCfgPortEdge OBJECT-TYPE
    SYNTAX INTEGER {
        enabled(1),
        disabled(2)
        }
    MAX-ACCESS read-create
    STATUS current
    DESCRIPTION
        "The state of port edge."
    ::= { stgNewCfgPortTableEntry 7 }

stgNewCfgPortFastFwd OBJECT-TYPE
    SYNTAX INTEGER {
        enabled(1),
        disabled(2)
        }
    MAX-ACCESS read-create
    STATUS current
    DESCRIPTION
        "The state of port fast forwarding."
    ::= { stgNewCfgPortTableEntry 8 }

-- MST Configuration 

mstCurCfgState	OBJECT-TYPE
    SYNTAX  INTEGER  {
	enabled(2),
	disabled(3)
	}
    MAX-ACCESS  read-only
    STATUS  current
    DESCRIPTION
        "Enable or disable MSTP/RSTP"
    ::= { mstGeneralCfg 1 }

mstNewCfgState	OBJECT-TYPE
    SYNTAX  INTEGER  {
	enabled(2),
	disabled(3)
	}
    MAX-ACCESS  read-write
    STATUS  current
    DESCRIPTION
        "Enable or disable MSTP/RSTP"
    ::= { mstGeneralCfg 2 }

mstCurCfgRegionName OBJECT-TYPE
   SYNTAX  DisplayString (SIZE (0..32))
   MAX-ACCESS  read-only
   STATUS  current
   DESCRIPTION
      "The Name for the Region's configuration."
   ::= { mstGeneralCfg 3 } 

mstNewCfgRegionName OBJECT-TYPE
   SYNTAX  DisplayString (SIZE (0..32))
   MAX-ACCESS  read-write
   STATUS  current
   DESCRIPTION
      "The Name for the Region's configuration."
   ::= { mstGeneralCfg 4 } 

mstCurCfgRegionVersion OBJECT-TYPE
    SYNTAX  INTEGER  (1..65535)
    MAX-ACCESS  read-only
    STATUS  current
    DESCRIPTION
        "Version of the MST Region."
    ::= { mstGeneralCfg 5 }

mstNewCfgRegionVersion OBJECT-TYPE
    SYNTAX  INTEGER  (1..65535)
    MAX-ACCESS  read-write
    STATUS  current
    DESCRIPTION
        "Version of the MST Region."
    ::= { mstGeneralCfg 6 }

mstCurCfgMaxHopCount OBJECT-TYPE
    SYNTAX  INTEGER  (6..60)
    MAX-ACCESS  read-only
    STATUS  current
    DESCRIPTION
        "Indicates the maximum hop count value."
    ::= { mstGeneralCfg 7 }

mstNewCfgMaxHopCount OBJECT-TYPE
    SYNTAX  INTEGER  (6..60)
    MAX-ACCESS  read-write
    STATUS  current
    DESCRIPTION
        "Indicates the maximum hop count value."
    ::= { mstGeneralCfg 8 }

mstCurCfgStpMode OBJECT-TYPE
    SYNTAX  INTEGER  {
	mstp(1),
	rstp(2)
	}
    MAX-ACCESS  read-only
    STATUS  current
    DESCRIPTION
        "The version of Spanning Tree Protocal the bridge is currently 
         running."
    ::= { mstGeneralCfg 9 }

mstNewCfgStpMode OBJECT-TYPE
    SYNTAX  INTEGER  {
	mstp(1),
	rstp(2)
	}
    MAX-ACCESS  read-write
    STATUS  current
    DESCRIPTION
        "The version of Spanning Tree Protocal the bridge is currently 
         running."
    ::= { mstGeneralCfg 10 }

mstCistDefaultCfg OBJECT-TYPE
    SYNTAX INTEGER {
        default(1)
        }
    MAX-ACCESS read-write
    STATUS current
    DESCRIPTION
        "Setting the value to default(1) will set the Multiple
         Spanning Tree and member parameters to default.  default(1) is 
         always returned when read, but it does not mean anything."
    ::= { mstCistCfg 1 }

-- CIST Brige Configuration
mstCistBridgeCfg  OBJECT IDENTIFIER ::= { mstCistCfg 2 }

mstCistCurCfgBridgePriority OBJECT-TYPE
    SYNTAX  INTEGER  (0..65535)
    MAX-ACCESS  read-only
    STATUS  current
    DESCRIPTION
        "The value of the writable portion of the Brigde Identifier comprising
         of the first two octets."
    ::= { mstCistBridgeCfg 1 }

mstCistNewCfgBridgePriority OBJECT-TYPE
    SYNTAX  INTEGER  (0..65535)
    MAX-ACCESS  read-write
    STATUS  current
    DESCRIPTION
        "The value of the writable portion of the Brigde Identifier comprising
         of the first two octets."
    ::= { mstCistBridgeCfg 2 }


mstCistCurCfgBridgeMaxAge OBJECT-TYPE
    SYNTAX  INTEGER  (6..40)
    MAX-ACCESS  read-only
    STATUS  current
    DESCRIPTION
        "The value in seconds that all bridges use for MaxAge when this bridge
         is acting as the root."
    ::= { mstCistBridgeCfg 5 }

mstCistNewCfgBridgeMaxAge OBJECT-TYPE
    SYNTAX  INTEGER  (6..40)
    MAX-ACCESS  read-write
    STATUS  current
    DESCRIPTION
        "The value in seconds that all bridges use for MaxAge when this bridge
         is acting as the root."
    ::= { mstCistBridgeCfg 6 }

mstCistCurCfgBridgeForwardDelay OBJECT-TYPE
    SYNTAX  INTEGER  (4..30)
    MAX-ACCESS  read-only
    STATUS  current
    DESCRIPTION
        "The value in seconds that all bridges use for ForwardDelay when this 
         bridge is acting as the root."
    ::= { mstCistBridgeCfg 7 }

mstCistNewCfgBridgeForwardDelay OBJECT-TYPE
    SYNTAX  INTEGER  (4..30)
    MAX-ACCESS  read-write
    STATUS  current
    DESCRIPTION
        "The value in seconds that all bridges use for ForwardDelay when this 
         bridge is acting as the root."
    ::= { mstCistBridgeCfg 8 }

mstCistCurCfgVlanBmap OBJECT-TYPE
    SYNTAX  OCTET STRING (SIZE(0..512)) 
    MAX-ACCESS  read-only
    STATUS  current
    DESCRIPTION
    "The vlans applied to the CIST group.  The vlans are 
     presented in bitmap format. This string displays vlan number
     from 1 to 4094.

     in receiving order:

         OCTET 1  OCTET 2  .....
             xxxxxxxx xxxxxxxx ..... 
             ||    || |_ vlan 9
             ||    ||  
             ||    ||___ vlan 8
             ||    |____ vlan 7
             ||      .    .   .
             ||_________ vlan 2
             |__________ vlan 1

         where x : 1 - The represented vlan applied to the CIST group. 
                   0 - The represented vlan not applied to the group"
    ::= { mstCistBridgeCfg 9 }

mstCistNewCfgVlanBmap OBJECT-TYPE
    SYNTAX  OCTET STRING (SIZE(0..512)) 
    MAX-ACCESS  read-only
    STATUS  current
    DESCRIPTION
    "The vlans applied to the CIST group.  The vlans are 
     presented in bitmap format. This string displays vlan number
     from 1 to 4094.

     in receiving order:

         OCTET 1  OCTET 2  .....
             xxxxxxxx xxxxxxxx ..... 
             ||    || |_ vlan 9
             ||    ||  
             ||    ||___ vlan 8
             ||    |____ vlan 7
             ||      .    .   .
             ||_________ vlan 2
             |__________ vlan 1

         where x : 1 - The represented vlan applied to the CIST group. 
                   0 - The represented vlan not applied to the group"
    ::= { mstCistBridgeCfg 10 }

mstCistNewCfgAddVlan OBJECT-TYPE
    SYNTAX  Integer32
    MAX-ACCESS  read-create
    STATUS  current
    DESCRIPTION
        "The vlan to be added to the CIST Group.  A 
         '0' value is returned when read." 
    ::= { mstCistBridgeCfg 11 }

-- CIST Port Configuration

mstCistCurCfgPortTable OBJECT-TYPE
    SYNTAX SEQUENCE OF MstCistCurCfgPortTableEntry
    MAX-ACCESS not-accessible
    STATUS current
    DESCRIPTION
        "The table of CIST Port configuration."
    ::= { mstCistCfg 3 }

mstCistCurCfgPortTableEntry OBJECT-TYPE
    SYNTAX MstCistCurCfgPortTableEntry
    MAX-ACCESS not-accessible
    STATUS current
    DESCRIPTION
        "Information about a particular CIST Port configuration."
    INDEX { mstCistCurCfgPortIndex }
    ::= { mstCistCurCfgPortTable 1 }

MstCistCurCfgPortTableEntry ::= SEQUENCE {
    mstCistCurCfgPortIndex      Integer32,
    mstCistCurCfgPortPriority   INTEGER,
    mstCistCurCfgPortPathCost   INTEGER,
    mstCistCurCfgPortLinkType   INTEGER,
    mstCistCurCfgPortEdge       INTEGER,
    mstCistCurCfgPortStpState   INTEGER,
    mstCistCurCfgPortHelloTime  INTEGER
    }

mstCistCurCfgPortIndex OBJECT-TYPE
    SYNTAX Integer32
    MAX-ACCESS read-only
    STATUS current
    DESCRIPTION
        "The port number of the port for which this entry contains spanning
         tree configuration."
    ::= { mstCistCurCfgPortTableEntry 1 }

mstCistCurCfgPortPriority OBJECT-TYPE
    SYNTAX INTEGER (0..240)
    MAX-ACCESS read-only
    STATUS current
    DESCRIPTION
        "The four most significant bits of the Port Identifier of the 
         Spanning Tree instance can be modified by setting this value."
    ::= { mstCistCurCfgPortTableEntry 2 }

mstCistCurCfgPortPathCost OBJECT-TYPE
    SYNTAX INTEGER (1..200000000)
    MAX-ACCESS read-only
    STATUS current
    DESCRIPTION
        "The contribution of this port to the path cost of paths towards 
         the CIST Root which include this port."
    ::= { mstCistCurCfgPortTableEntry 3 }

mstCistCurCfgPortLinkType OBJECT-TYPE
    SYNTAX INTEGER {
        auto(1),
        p2p(2),
        shared(3)
        }
    MAX-ACCESS read-only
    STATUS current
    DESCRIPTION
        "The administrative point-to-point status of the LAN segment attached 
         to this port.  A value of p2p (2) indicates that this port should 
         always be treated as if it is connected to a point-to-point link. 
         A value of shared(3) indicates that this port should be treated as 
         having a shared media connection.  A value of auto(1) indicates that 
         this port is considered to have a point-to-point link if it is an 
         Aggregator and all of its members are aggregatable, or if the MAC 
         entity is configured for full duplex operation, either through
         auto-negotiation or by management means."    
    ::= { mstCistCurCfgPortTableEntry 4 }

mstCistCurCfgPortEdge OBJECT-TYPE
    SYNTAX INTEGER {
        enabled(1),
        disabled(2)
        }
    MAX-ACCESS read-only
    STATUS current
    DESCRIPTION
        "The value of the Edge Port parameter."
    ::= { mstCistCurCfgPortTableEntry 5 }

mstCistCurCfgPortStpState OBJECT-TYPE
    SYNTAX INTEGER {
        on(1),
        off(2)
        }
    MAX-ACCESS read-only
    STATUS current
    DESCRIPTION
        "Turn port's Spanning Tree on/off."
    ::= { mstCistCurCfgPortTableEntry 6 }

mstCistCurCfgPortHelloTime OBJECT-TYPE
    SYNTAX  INTEGER (1..10)
    MAX-ACCESS  read-only
    STATUS  current
    DESCRIPTION
        "The amount of time between the transmission of Configuration Port 
         PDUs in seconds."
    ::= { mstCistCurCfgPortTableEntry 7 } 

mstCistNewCfgPortTable OBJECT-TYPE
    SYNTAX SEQUENCE OF MstCistNewCfgPortTableEntry
    MAX-ACCESS not-accessible
    STATUS current
    DESCRIPTION
        "The table of CIST Port configuration."
    ::= { mstCistCfg 4 }

mstCistNewCfgPortTableEntry OBJECT-TYPE
    SYNTAX MstCistNewCfgPortTableEntry
    MAX-ACCESS not-accessible
    STATUS current
    DESCRIPTION
        "Information about a particular CIST Port configuration."
    INDEX { mstCistNewCfgPortIndex }
    ::= { mstCistNewCfgPortTable 1 }

MstCistNewCfgPortTableEntry ::= SEQUENCE {
    mstCistNewCfgPortIndex      Integer32,
    mstCistNewCfgPortPriority   INTEGER,
    mstCistNewCfgPortPathCost   INTEGER,
    mstCistNewCfgPortLinkType   INTEGER,
    mstCistNewCfgPortEdge       INTEGER,
    mstCistNewCfgPortStpState   INTEGER,
    mstCistNewCfgPortHelloTime  INTEGER
    }

mstCistNewCfgPortIndex OBJECT-TYPE
    SYNTAX Integer32
    MAX-ACCESS read-only
    STATUS current
    DESCRIPTION
        "The port number of the port for which this entry contains spanning
         tree configuration."
    ::= { mstCistNewCfgPortTableEntry 1 }

mstCistNewCfgPortPriority OBJECT-TYPE
    SYNTAX INTEGER (0..240)
    MAX-ACCESS read-create
    STATUS current
    DESCRIPTION
        "The four most significant bits of the Port Identifier of the 
         Spanning Tree instance can be modified by setting this value."
    ::= { mstCistNewCfgPortTableEntry 2 }

mstCistNewCfgPortPathCost OBJECT-TYPE
    SYNTAX INTEGER (1..200000000)
    MAX-ACCESS read-create
    STATUS current
    DESCRIPTION
        "The contribution of this port to the path cost of paths towards 
         the CIST Root which include this port."
    ::= { mstCistNewCfgPortTableEntry 3 }

mstCistNewCfgPortLinkType OBJECT-TYPE
    SYNTAX INTEGER {
        auto(1),
        p2p(2),
        shared(3)
        }
    MAX-ACCESS read-create
    STATUS current
    DESCRIPTION
        "The administrative point-to-point status of the LAN segment attached 
         to this port.  A value of p2p (2) indicates that this port should 
         always be treated as if it is connected to a point-to-point link. 
         A value of shared(3) indicates that this port should be treated as 
         having a shared media connection.  A value of auto(1) indicates that 
         this port is considered to have a point-to-point link if it is an 
         Aggregator and all of its members are aggregatable, or if the MAC 
         entity is configured for full duplex operation, either through
         auto-negotiation or by management means."    
    ::= { mstCistNewCfgPortTableEntry 4 }

mstCistNewCfgPortEdge OBJECT-TYPE
    SYNTAX INTEGER {
        enabled(1),
        disabled(2)
        }
    MAX-ACCESS read-create
    STATUS current
    DESCRIPTION
        "The value of the Edge Port parameter."
    ::= { mstCistNewCfgPortTableEntry 5 }

mstCistNewCfgPortStpState OBJECT-TYPE
    SYNTAX INTEGER {
        on(1),
        off(2)
        }
    MAX-ACCESS read-create
    STATUS current
    DESCRIPTION
        "Turn port's Spanning Tree on/off."
    ::= { mstCistNewCfgPortTableEntry 6 }

mstCistNewCfgPortHelloTime OBJECT-TYPE
    SYNTAX  INTEGER (1..10)
    MAX-ACCESS  read-create
    STATUS  current
    DESCRIPTION
        "The amount of time between the transmission of Configuration Port 
         PDUs in seconds."
    ::= { mstCistNewCfgPortTableEntry 7 } 

-- Complete Port Mirroring 
pmCurCfgPortMirrState OBJECT-TYPE
    SYNTAX  INTEGER {
	enabled(1),
	disabled(2)
	}
    MAX-ACCESS  read-only
    STATUS  current
    DESCRIPTION
        "The state of port-based port mirroring."
    ::= { mirrPortMirr 1 }
 
pmNewCfgPortMirrState OBJECT-TYPE
    SYNTAX  INTEGER {
	enabled(1),
	disabled(2)
        }
    MAX-ACCESS  read-write
    STATUS  current
    DESCRIPTION
        "The state of port-based port mirroring."
    ::= { mirrPortMirr 2 }

pmCurCfgPortMonitorTable OBJECT-TYPE
    SYNTAX  SEQUENCE OF PmCurCfgPortMonitorEntry
    MAX-ACCESS  not-accessible
    STATUS  current
    DESCRIPTION
        "The table of monitoring ports."
    ::= { mirrPortMirr 3 }

pmCurCfgPortMonitorEntry OBJECT-TYPE
    SYNTAX  PmCurCfgPortMonitorEntry
    MAX-ACCESS  not-accessible
    STATUS  current
    DESCRIPTION
        "A row in the monitoring port table."
    INDEX   { pmCurCfgPmirrMoniPortIndex, pmCurCfgPmirrMirrPortIndex }
    ::= { pmCurCfgPortMonitorTable 1 }

PmCurCfgPortMonitorEntry ::= SEQUENCE {
    pmCurCfgPmirrMoniPortIndex       Integer32,
    pmCurCfgPmirrMirrPortIndex       Integer32,
    pmCurCfgPmirrDirection           INTEGER
    }

pmCurCfgPmirrMoniPortIndex OBJECT-TYPE
    SYNTAX  Integer32
    MAX-ACCESS  read-only
    STATUS  current
    DESCRIPTION
        "The monitoring port number." 
    ::= { pmCurCfgPortMonitorEntry 1 }

pmCurCfgPmirrMirrPortIndex OBJECT-TYPE 
    SYNTAX  Integer32 
    MAX-ACCESS  read-only 
    STATUS  current 
    DESCRIPTION 
        "The mirrored port number" 
    ::= { pmCurCfgPortMonitorEntry 2 }

pmCurCfgPmirrDirection OBJECT-TYPE
    SYNTAX  INTEGER {
	in(1),
	out(2),
	both(3)
        }
    MAX-ACCESS  read-only
    STATUS  current
    DESCRIPTION
        "The type of traffic to be monitored with respect to the
         mirrored port."
    ::= { pmCurCfgPortMonitorEntry 3 }


pmNewCfgPortMonitorTable OBJECT-TYPE
    SYNTAX  SEQUENCE OF PmNewCfgPortMonitorEntry
    MAX-ACCESS  not-accessible
    STATUS  current
    DESCRIPTION
        "The table of monitoring ports."
    ::= { mirrPortMirr 4 }

pmNewCfgPortMonitorEntry OBJECT-TYPE
    SYNTAX  PmNewCfgPortMonitorEntry
    MAX-ACCESS  not-accessible
    STATUS  current
    DESCRIPTION
        "A row in the monitoring port table."
    INDEX   { pmNewCfgPmirrMoniPortIndex, pmNewCfgPmirrMirrPortIndex }
    ::= { pmNewCfgPortMonitorTable 1 }

PmNewCfgPortMonitorEntry ::= SEQUENCE {
    pmNewCfgPmirrMoniPortIndex          Integer32,
    pmNewCfgPmirrMirrPortIndex          Integer32,
    pmNewCfgPmirrDirection              INTEGER,
    pmNewCfgPmirrDelete                 INTEGER,
    pmNewCfgPmonDelete                 INTEGER
    }

pmNewCfgPmirrMoniPortIndex OBJECT-TYPE
    SYNTAX  Integer32
    MAX-ACCESS  read-only
    STATUS  current
    DESCRIPTION
        "The monitoring port number." 
    ::= { pmNewCfgPortMonitorEntry 1 }

pmNewCfgPmirrMirrPortIndex OBJECT-TYPE 
    SYNTAX  Integer32 
    MAX-ACCESS  read-only 
    STATUS  current 
    DESCRIPTION 
        "The mirrored port number" 
    ::= { pmNewCfgPortMonitorEntry 2 }

pmNewCfgPmirrDirection OBJECT-TYPE
    SYNTAX  INTEGER {
	in(1),
	out(2),
	both(3)
        }
    MAX-ACCESS  read-create
    STATUS  current
    DESCRIPTION
        "The type of traffic to be monitored with respect to the
         mirrored port."
    ::= { pmNewCfgPortMonitorEntry 3 }

pmNewCfgPmirrDelete OBJECT-TYPE
    SYNTAX  INTEGER  {
        other(1),
        delete(2)
        }
    MAX-ACCESS  read-create
    STATUS  current
    DESCRIPTION
        "Setting the value to delete(2) will delete the entire
         row. When read, other(1) is returned."
    ::= { pmNewCfgPortMonitorEntry 4 }


pmNewCfgPmonDelete OBJECT-TYPE
    SYNTAX  INTEGER  {
        other(1),
        delete(2)
        }
    MAX-ACCESS  read-create
    STATUS  current
    DESCRIPTION
        "Setting the value to delete(2) will delete the monitor
         port. When read, other(1) is returned."
    ::= { pmNewCfgPortMonitorEntry 10 }


-- L2 general

upfastCurCfgState OBJECT-TYPE
    SYNTAX  INTEGER  {
        enable(1),
        disable(2)
        }
    MAX-ACCESS  read-only
    STATUS  current
    DESCRIPTION
        "Enable or disable uplink fast"
    ::= { l2GeneralCfg 1 }

upfastNewCfgState OBJECT-TYPE
    SYNTAX  INTEGER  {
        enable(1),
        disable(2)
        }
    MAX-ACCESS  read-write
    STATUS  current
    DESCRIPTION
        "Enable or disable uplink fast"
    ::= { l2GeneralCfg 2 }

updateCurCfgState OBJECT-TYPE
    SYNTAX  INTEGER  (10..200)
    MAX-ACCESS  read-only
    STATUS  current
    DESCRIPTION
        "UplinkFast station update rate: packets per second"
    ::= { l2GeneralCfg 3 }

updateNewCfgState OBJECT-TYPE
    SYNTAX  INTEGER  (10..200)
    MAX-ACCESS  read-write
    STATUS  current
    DESCRIPTION
        "UplinkFast station update rate: packets per second"
    ::= { l2GeneralCfg 4 }

-- FDB Statistics
 
fdbStatsCreates OBJECT-TYPE
    SYNTAX  Counter32
    MAX-ACCESS  read-only
    STATUS  current
    DESCRIPTION
        "Number of entries created in the Forwarding Database."
    ::= { fdbStats 1 }

fdbStatsDeletes OBJECT-TYPE
    SYNTAX  Counter32
    MAX-ACCESS  read-only
    STATUS  current
    DESCRIPTION
        "Number of entries deleted from the Forwarding Database."
    ::= { fdbStats 2 }

fdbStatsCurrent OBJECT-TYPE
    SYNTAX  Gauge32
    MAX-ACCESS  read-only
    STATUS  current
    DESCRIPTION
        "Current number of entries in the Forwarding Database."
    ::= { fdbStats 3 }

fdbStatsHiwat OBJECT-TYPE
    SYNTAX  Integer32
    MAX-ACCESS  read-only
    STATUS  current
    DESCRIPTION
        "Highest number of entries recorded at any given time in the 
         Forwarding Database."
    ::= { fdbStats 4 }

fdbStatsLookups OBJECT-TYPE
    SYNTAX  Counter32
    MAX-ACCESS  read-only
    STATUS  current
    DESCRIPTION
        "Number of entry lookups in the Forwarding Database."
    ::= { fdbStats 5 }

fdbStatsLookupFails OBJECT-TYPE
    SYNTAX  Counter32
    MAX-ACCESS  read-only
    STATUS  current
    DESCRIPTION
        "Number of unsuccessful searches made in the Forwarding Database."
    ::= { fdbStats 6 }

fdbStatsFinds OBJECT-TYPE
    SYNTAX  Counter32
    MAX-ACCESS  read-only
    STATUS  current
    DESCRIPTION
        "Number of searches in the Forwarding Database."
    ::= { fdbStats 7 }

fdbStatsFindFails OBJECT-TYPE
    SYNTAX  Counter32
    MAX-ACCESS  read-only
    STATUS  current
    DESCRIPTION
        "Number of search failures in the Forwarding Database."
    ::= { fdbStats 8 }

fdbStatsFindOrCreates OBJECT-TYPE
    SYNTAX  Counter32
    MAX-ACCESS  read-only
    STATUS  current
    DESCRIPTION
        "Number of entries found or created in the Forwarding Database."
    ::= { fdbStats 9 }

fdbStatsOverflows OBJECT-TYPE
    SYNTAX  Counter32
    MAX-ACCESS  read-only
    STATUS  current
    DESCRIPTION
        "Number of entries overflowing the Forwarding Database."
    ::= { fdbStats 10 }

-- STP Statistics

stgStatsPortTable OBJECT-TYPE
    SYNTAX SEQUENCE OF StgStatsPortTableEntry
    MAX-ACCESS not-accessible
    STATUS current
    DESCRIPTION
        "The table of Spanning Tree Group port statistics."
    ::= { stpStats 1 }

stgStatsPortTableEntry OBJECT-TYPE
    SYNTAX StgStatsPortTableEntry
    MAX-ACCESS not-accessible
    STATUS current
    DESCRIPTION
        "Statistics about port of a particular Spanning Tree Group."
    INDEX { stgStatsStpIndex, stgStatsPortIndex }
    ::= { stgStatsPortTable 1 }

StgStatsPortTableEntry ::= SEQUENCE {
    stgStatsStpIndex            Integer32,
    stgStatsPortIndex	        Integer32,
    stgStatsPortRcvCfgBpdus     Counter32,
    stgStatsPortRcvTcnBpdus     Counter32,
    stgStatsPortXmtCfgBpdus     Counter32,
    stgStatsPortXmtTcnBpdus     Counter32 
    }

stgStatsStpIndex OBJECT-TYPE
    SYNTAX Integer32  
    MAX-ACCESS read-only
    STATUS current
    DESCRIPTION
        "The identifier of a particular Spanning Tree Group."
    ::= { stgStatsPortTableEntry 1 }

stgStatsPortIndex OBJECT-TYPE
    SYNTAX Integer32
    MAX-ACCESS read-only
    STATUS current
    DESCRIPTION
        "The port identifier of a particular Spanning Tree Group."
    ::= { stgStatsPortTableEntry 2 }

stgStatsPortRcvCfgBpdus OBJECT-TYPE
    SYNTAX Counter32 
    MAX-ACCESS read-only
    STATUS current
    DESCRIPTION
        "Number of Configuration BPDU's received on this port."
    ::= { stgStatsPortTableEntry 3 }

stgStatsPortRcvTcnBpdus OBJECT-TYPE
    SYNTAX Counter32 
    MAX-ACCESS read-only
    STATUS current
    DESCRIPTION
        "Number of TCN BPDU's received on this port."
    ::= { stgStatsPortTableEntry 4 }

stgStatsPortXmtCfgBpdus OBJECT-TYPE
    SYNTAX Counter32 
    MAX-ACCESS read-only
    STATUS current
    DESCRIPTION
        "Number of Configuration BPDU's trasmitted from the port."
    ::= { stgStatsPortTableEntry 5 }

stgStatsPortXmtTcnBpdus OBJECT-TYPE
    SYNTAX Counter32 
    MAX-ACCESS read-only
    STATUS current
    DESCRIPTION
        "Number of TCN BPDU's trasmitted from the port."
    ::= { stgStatsPortTableEntry 6 }




-- UFD stats

ufdNoLtMLinkFailure OBJECT-TYPE
  SYNTAX Integer32
  MAX-ACCESS read-only
  STATUS current
  DESCRIPTION
	" "
  ::= {ufdStats 1}

ufdNoLtMLinkBlockingState OBJECT-TYPE
  SYNTAX Integer32
  MAX-ACCESS read-only
  STATUS current
  DESCRIPTION
	" "
  ::= {ufdStats 2}

ufdNoLtDAutoDisabled OBJECT-TYPE
  SYNTAX Integer32
  MAX-ACCESS read-only
  STATUS current
  DESCRIPTION
	" "
  ::= {ufdStats 3}



-- FDB stats



fdbClear OBJECT-TYPE
    SYNTAX  INTEGER {
        ok(1),
        clear(2)
        }
    MAX-ACCESS  read-write
    STATUS  current 
    DESCRIPTION
        "Setting this value to clear(2) clears the entire master FDB."
    ::= { fdbInfo 1 }

fdbTable OBJECT-TYPE
    SYNTAX  SEQUENCE OF FdbEntry
    MAX-ACCESS  not-accessible
    STATUS  current
    DESCRIPTION
        "The table of FDB entries."
    ::= { fdbInfo 2 }

fdbEntry OBJECT-TYPE
    SYNTAX  FdbEntry
    MAX-ACCESS  not-accessible
    STATUS  current
    DESCRIPTION
        "A row in the FDB table"
    INDEX   { fdbMacAddr }
    ::= { fdbTable 1 }

FdbEntry ::= SEQUENCE {
    fdbMacAddr            PhysAddress,
    fdbVlan       	  Integer32,
    fdbSrcPort            Integer32,
    fdbSrcTrunk           Integer32,
    fdbState              INTEGER,
    fdbRefSps             DisplayString,
    fdbLearnedPort        Integer32
    }

fdbMacAddr OBJECT-TYPE
    SYNTAX  PhysAddress
    MAX-ACCESS  read-only
    STATUS  current
    DESCRIPTION
        "The MAC address for the FDB entry."
    ::= { fdbEntry 1 }

fdbVlan OBJECT-TYPE 
    SYNTAX  Integer32 
    MAX-ACCESS  read-only 
    STATUS  current 
    DESCRIPTION 
        "The VLAN ID for the FDB entry." 
    ::= { fdbEntry 2 }

fdbSrcPort OBJECT-TYPE  
    SYNTAX  Integer32 
    MAX-ACCESS  read-only  
    STATUS  current  
    DESCRIPTION  
       "Either the value '0', or the port number of the port on which a frame 
        having a source address equal to the value of the corresponding 
        instance has been seen.  A value of '0' indicates that the port 
        number has not been learned but that the bridge does have some
        forwarding/filtering information about this address."
    ::= { fdbEntry 3 }

fdbState OBJECT-TYPE  
    SYNTAX  INTEGER {
        unknown(1),
        ignore(2),
        forward(3),
        flood(4),
        ffd(5),
        trunk(6),
        vir(7),
        vsr(8),
        vpr(9),
        other(10)
        }
    MAX-ACCESS  read-only  
    STATUS  current  
    DESCRIPTION  
        "The state of the FDB entry. The meanings of the values are :
         unknown(1) : the MAC address has not yet been learned by the switch
                      but has only been seen as a destination address
         forward(3) : the MAC address has been learned by the switch
         flood(4)   : the MAC address is a multicast destination address 
         trunk(6)   : frames with this MAC address are forwarded to trunk
                      group
         vir(7)     : frames with this MAC address are forwarded for L3 
                      processing"
    ::= { fdbEntry 4 }

fdbRefSps OBJECT-TYPE   
    SYNTAX  DisplayString (SIZE(0..32))
    MAX-ACCESS  read-only   
    STATUS  current   
    DESCRIPTION   
        "The referenced SPs associated with this FDB entry."   
    ::= { fdbEntry 5 }

fdbLearnedPort OBJECT-TYPE   
    SYNTAX  Integer32  
    MAX-ACCESS  read-only   
    STATUS  current   
    DESCRIPTION   
        "The learned port associated with this FDB entry."   
    ::= { fdbEntry 6 }

fdbSrcTrunk OBJECT-TYPE
    SYNTAX  Integer32
    MAX-ACCESS  read-only
    STATUS  current
    DESCRIPTION
       "Either the value '0', or the trunk number of the trunk on which a frame
        having a source address equal to the value of the corresponding
        instance has been seen.  A value of '0' indicates that the source
        address is not associated with a trunk."
    ::= { fdbEntry 7 }


-- STP information

stpInfoTable OBJECT-TYPE
    SYNTAX SEQUENCE OF StpInfoTableEntry
    MAX-ACCESS not-accessible
    STATUS current
    DESCRIPTION
        "The table of Spanning Tree Group information."
    ::= { stpInfo 1 }

stpInfoTableEntry OBJECT-TYPE
    SYNTAX StpInfoTableEntry
    MAX-ACCESS not-accessible
    STATUS current
    DESCRIPTION
        "Information about a particular Spanning Tree Group."
    INDEX { stpInfoIndex }
    ::= { stpInfoTable 1 }

StpInfoTableEntry ::= SEQUENCE {
    stpInfoIndex              Integer32,
    stpInfoState              INTEGER,
    stgInfoVlanBmap           OCTET STRING,
    stpInfoTimeSinceTopChange TimeTicks,
    stpInfoTopChanges         Counter32,
    stpInfoDesignatedRoot     BridgeId,
    stpInfoRootCost           Integer32,
    stpInfoRootPort           Integer32,
    stpInfoHelloTime          Integer32,
    stpInfoMaxAge             Integer32,
    stpInfoForwardDelay       Integer32,
    stpInfoHoldTime           Integer32,
    stpInfoBrgPriority        INTEGER,
    stpInfoBrgHelloTime       INTEGER,
    stpInfoBrgForwardDelay    INTEGER,
    stpInfoBrgMaxAge          INTEGER,
    stpInfoAgingTime          INTEGER
    }

stpInfoIndex OBJECT-TYPE
    SYNTAX Integer32
    MAX-ACCESS read-only
    STATUS current
    DESCRIPTION
        "The identifier of a particular Spanning Tree Group.  This is also
         index to the entLogicalTable of Entity MIB."
    ::= { stpInfoTableEntry 1 }

stpInfoState OBJECT-TYPE
    SYNTAX INTEGER {
        on(1),
        off(2)
        }
    MAX-ACCESS read-only
    STATUS current
    DESCRIPTION
        "Turn on of off Spanning Tree operation of a particular Spanning
         Tree Group."
    ::= { stpInfoTableEntry 2 }

stgInfoVlanBmap OBJECT-TYPE
    SYNTAX  OCTET STRING (SIZE(0..512)) 
    MAX-ACCESS  read-only
    STATUS  current
    DESCRIPTION
        "The vlans applied to the spanning tree group.  The vlans are 
         presented in bitmap format. This string displays vlan number
         from 1 to 4096.

         in receiving order:

             OCTET 1  OCTET 2  .....
             xxxxxxxx xxxxxxxx ..... 
             ||    || |_ vlan 9
             ||    ||  
             ||    ||___ vlan 8
             ||    |____ vlan 7
             ||      .    .   .
             ||_________ vlan 2
             |__________ vlan 1 (as index to stgCurCfgTable)

         where x : 1 - The represented vlan applied to the spanning tree. 
                   0 - The represented vlan not applied to the spanning tree"
    ::= { stpInfoTableEntry 3 }

stpInfoTimeSinceTopChange OBJECT-TYPE
    SYNTAX  TimeTicks
    MAX-ACCESS  read-only
    STATUS  current
    DESCRIPTION
        "The time (in hundredths of a second) since the last time a topology 
         change was detected by the bridge entity."
    ::= { stpInfoTableEntry 4 }

stpInfoTopChanges OBJECT-TYPE
    SYNTAX  Counter32
    MAX-ACCESS  read-only
    STATUS  current
    DESCRIPTION
        "The total number of topology changes detected by this bridge since 
         the management entity was last reset or initialized."
    ::= { stpInfoTableEntry 5 }

stpInfoDesignatedRoot OBJECT-TYPE
    SYNTAX  BridgeId
    MAX-ACCESS  read-only
    STATUS  current
    DESCRIPTION
        "The bridge identifier of the root of the spanning tree as determined 
         by the Spanning Tree Protocol as executed by this node.  This value 
         is used as the Root Identifier parameter in all Configuration Bridge 
         PDUs originated by this node."
    ::= { stpInfoTableEntry 6 }

stpInfoRootCost OBJECT-TYPE
    SYNTAX  Integer32
    MAX-ACCESS  read-only
    STATUS  current
    DESCRIPTION
        "The cost of the path to the root as seen from this bridge."
    ::= { stpInfoTableEntry 7 }

stpInfoRootPort OBJECT-TYPE
    SYNTAX  Integer32
    MAX-ACCESS  read-only
    STATUS  current
    DESCRIPTION
        "The port number of the port which offers the lowest cost path from 
         this bridge to the root bridge."
    ::= { stpInfoTableEntry 8 }

stpInfoMaxAge OBJECT-TYPE
    SYNTAX  Integer32
    MAX-ACCESS  read-only
    STATUS  current
    DESCRIPTION
        "The maximum age of Spanning Tree Protocol information learned from 
         the network on any port before it is discarded, in units of 
         hundredths of a second.  This is the actual value that this bridge is
         currently using."
    ::= { stpInfoTableEntry 9 }

stpInfoHelloTime OBJECT-TYPE
    SYNTAX  Integer32
    MAX-ACCESS  read-only
    STATUS  current
    DESCRIPTION
        "The amount of time between the transmission of Configuration bridge 
         PDUs by this node on any port when it is the root of the spanning 
         tree or trying to become so, in units of hundredths of a second.
         This is the actual value that this bridge is currently using."
    ::= { stpInfoTableEntry 10 }

stpInfoForwardDelay OBJECT-TYPE
     SYNTAX  Integer32
     MAX-ACCESS  read-only
     STATUS  current
     DESCRIPTION
         "This time value, measured in units of hundredths of a second, 
          controls how fast a port changes its spanning state when moving 
          towards the Forwarding state.  The value determines how long the port
          stays in each of the Listening and Learning states, which precede 
          the Forwarding state.  This value is also used, when a topology 
          change has been detected and is underway, to age all dynamic entries
          in the Forwarding Database."
    ::= { stpInfoTableEntry 11 }

stpInfoHoldTime OBJECT-TYPE
    SYNTAX  Integer32
    MAX-ACCESS  read-only
    STATUS  current
    DESCRIPTION
        "This time value determines the interval length during which no more 
         than two Configuration bridge PDUs shall be transmitted by this node,
         in units of hundredths of a second."
    ::= { stpInfoTableEntry 12 }

stpInfoBrgPriority OBJECT-TYPE
    SYNTAX  INTEGER (0..65535)
    MAX-ACCESS  read-only
    STATUS  current
    DESCRIPTION
        "The value of the write-able portion of the Bridge ID, i.e., the first
         two octets of the (8 octet long) Bridge ID."
    ::= { stpInfoTableEntry 13 }

stpInfoBrgHelloTime OBJECT-TYPE
    SYNTAX  INTEGER (1..10)
    MAX-ACCESS  read-only
    STATUS  current
    DESCRIPTION
        "The value in seconds that all bridges use for HelloTime when this 
         bridge is acting as the root."
    ::= { stpInfoTableEntry 14 }

stpInfoBrgForwardDelay OBJECT-TYPE
    SYNTAX  INTEGER (4..30)
    MAX-ACCESS  read-only
    STATUS  current
    DESCRIPTION
        "The value in seconds that all bridges use for ForwardDelay when this 
         bridge is acting as the root."
    ::= { stpInfoTableEntry 15 }

stpInfoBrgMaxAge OBJECT-TYPE
    SYNTAX  INTEGER (6..40)
    MAX-ACCESS  read-only
    STATUS  current
    DESCRIPTION
        "The value in seconds that all bridges use for MaxAge when this bridge
         is acting as the root."
    ::= { stpInfoTableEntry 16 }

stpInfoAgingTime OBJECT-TYPE
    SYNTAX  INTEGER (0..65535)
    MAX-ACCESS  read-only
    STATUS  current
    DESCRIPTION
        "The timeout period in seconds for aging out dynamically learned 
         forwarding information."
    ::= { stpInfoTableEntry 17 }

stpInfoPortTable OBJECT-TYPE
    SYNTAX SEQUENCE OF StpInfoPortTableEntry
    MAX-ACCESS not-accessible
    STATUS current
    DESCRIPTION
        "The table of Spanning Tree Group port information."
    ::= { stpInfo 2 }

stpInfoPortTableEntry OBJECT-TYPE
    SYNTAX StpInfoPortTableEntry
    MAX-ACCESS not-accessible
    STATUS current
    DESCRIPTION
        "Information about port configuration for a particular Spanning Tree
         Group."
    INDEX { stpInfoPortStpIndex, stpInfoPortIndex }
    ::= { stpInfoPortTable 1 }

StpInfoPortTableEntry ::= SEQUENCE {
    stpInfoPortStpIndex           Integer32,
    stpInfoPortIndex              Integer32,
    stpInfoPortState              INTEGER,
    stpInfoPortDesignatedRoot     BridgeId,
    stpInfoPortDesignatedCost     Integer32,
    stpInfoPortDesignatedBridge   BridgeId,
    stpInfoPortDesignatedPort     OCTET STRING,
    stpInfoPortForwardTransitions Counter32,
    stpInfoPortPathCost           Integer32
   }

stpInfoPortStpIndex OBJECT-TYPE
    SYNTAX Integer32
    MAX-ACCESS read-only
    STATUS current
    DESCRIPTION
        "The identifier of a particular Spanning Tree Group."
    ::= { stpInfoPortTableEntry 1 }

stpInfoPortIndex OBJECT-TYPE
    SYNTAX Integer32
    MAX-ACCESS read-only
    STATUS current
    DESCRIPTION
        "The port identifier of a particular Spanning Tree Group."
    ::= { stpInfoPortTableEntry 2 }

stpInfoPortState OBJECT-TYPE
    SYNTAX  INTEGER {
        disabled(1),
        blocking(2),
        listening(3),
        learning(4),
        forwarding(5),
        broken(6)
        }
    MAX-ACCESS  read-only
    STATUS  current
    DESCRIPTION
        "The port's current state as defined by application of the Spanning 
         Tree Protocol.  This state controls what action a port takes on
         reception of a frame.  If the bridge has detected a port that is 
         malfunctioning it will place that port into the broken(6) state.  
         For ports which are disabled, this object will have a value of 
         disabled(1)."
    ::= { stpInfoPortTableEntry 3 }

stpInfoPortDesignatedRoot OBJECT-TYPE
    SYNTAX  BridgeId
    MAX-ACCESS  read-only
    STATUS  current
    DESCRIPTION
        "The unique Bridge Identifier of the Bridge recorded as the Root in 
         the Configuration BPDUs transmitted by the Designated Bridge for the
         segment to which the port is attached."
    ::= { stpInfoPortTableEntry 4 }

stpInfoPortDesignatedCost OBJECT-TYPE
    SYNTAX  Integer32
    MAX-ACCESS  read-only
    STATUS  current
    DESCRIPTION
        "The path cost of the Designated Port of the segment connected to this
         port.  This value is compared to the Root Path Cost field in received
         bridge PDUs."
    ::= { stpInfoPortTableEntry 5 }

stpInfoPortDesignatedBridge OBJECT-TYPE
    SYNTAX  BridgeId
    MAX-ACCESS  read-only
    STATUS  current
    DESCRIPTION
        "The Bridge Identifier of the bridge which this port considers to be 
         the Designated Bridge for this port's segment."
    ::= { stpInfoPortTableEntry 6 }

stpInfoPortDesignatedPort OBJECT-TYPE
    SYNTAX  OCTET STRING (SIZE (2))
    MAX-ACCESS  read-only
    STATUS  current
    DESCRIPTION
        "The Port Identifier of the port on the Designated Bridge for this 
         port's segment."
    ::= { stpInfoPortTableEntry 7 }

stpInfoPortForwardTransitions OBJECT-TYPE
    SYNTAX  Counter32
    MAX-ACCESS  read-only
    STATUS  current
    DESCRIPTION
        "The number of times this port has transitioned from the Learning 
         state to the Forwarding state."
    ::= { stpInfoPortTableEntry 8 }

stpInfoPortPathCost OBJECT-TYPE
    SYNTAX  Integer32
    MAX-ACCESS  read-only
    STATUS  current
    DESCRIPTION
        "The path cost of the port."
    ::= { stpInfoPortTableEntry 9 }

-- CIST Information

cistRoot OBJECT-TYPE
    SYNTAX  BridgeId
    MAX-ACCESS  read-only
    STATUS  current
    DESCRIPTION
        "The bridge identifier of the Root of the common spanning
         tree as determined by the Spanning Tree Protocol
         as executed by this node.  This value is used as
         the CIST Root Identifier parameter in all Configuration
         Bridge PDUs originated by this node."
    ::= { cistGeneralInfo 1 } 

cistRootPathCost OBJECT-TYPE
    SYNTAX  Integer32
    MAX-ACCESS  read-only
    STATUS  current
    DESCRIPTION
        "The cost of the path to the CIST Root as seen from this bridge."
    ::= { cistGeneralInfo 2 } 

cistRootPort OBJECT-TYPE
    SYNTAX  Integer32
    MAX-ACCESS  read-only
    STATUS  current
    DESCRIPTION 
        "The Port Number of the Port which offers the lowest path cost from 
        this bridge to the CIST Root Bridge."
    ::= { cistGeneralInfo 3 } 

cistRootHelloTime OBJECT-TYPE
    SYNTAX  Integer32
    MAX-ACCESS  read-only
    STATUS  current
    DESCRIPTION
        "The amount of time between the transmission of Configuration bridge
         PDUs in seconds."
    ::= { cistGeneralInfo 4 } 

cistRootMaxAge OBJECT-TYPE
    SYNTAX  Integer32
    MAX-ACCESS  read-only
    STATUS  current
    DESCRIPTION
        "The value in seconds that all bridges use for MaxAge when this bridge
         is acting as the root."
    ::= { cistGeneralInfo 5 } 

cistRootForwardDelay OBJECT-TYPE
    SYNTAX  Integer32
    MAX-ACCESS  read-only
    STATUS  current
    DESCRIPTION
        "The value in seconds that all bridges use for ForwardDelay when this 
         bridge is acting as the root."
    ::= { cistGeneralInfo 6 } 

cistRegionalRoot OBJECT-TYPE
    SYNTAX  BridgeId
    MAX-ACCESS  read-only
    STATUS  current
    DESCRIPTION
        "The bridge identifier of the Root of the Multiple
         spanning tree region as determined by the Spanning Tree
         Protocol as executed by this node.  This value is used as
         the CIST Regional Root Identifier parameter in all Configuration
         Bridge PDUs originated by this node."
   ::= { cistGeneralInfo 7 } 

cistRegionalPathCost OBJECT-TYPE
    SYNTAX  Integer32
    MAX-ACCESS  read-only
    STATUS  current
    DESCRIPTION
        "The Cost of the path to the CIST Regional Root as seen from this 
         bridge."
   ::= { cistGeneralInfo 8 } 

cistBridgePriority OBJECT-TYPE
    SYNTAX  INTEGER  (0..65535)
    MAX-ACCESS  read-only
    STATUS  current
    DESCRIPTION
        "The value of the writable portion of the Brigde Identifier comprising
         of the first two octets."
    ::= { cistGeneralInfo 9 }

cistBridgeMaxAge OBJECT-TYPE
    SYNTAX  INTEGER  (6..40)
    MAX-ACCESS  read-only
    STATUS  current
    DESCRIPTION
        "The value in seconds that all bridges use for MaxAge when this bridge
         is acting as the root."
    ::= { cistGeneralInfo 10 }

cistBridgeForwardDelay OBJECT-TYPE
    SYNTAX  INTEGER  (4..30)
    MAX-ACCESS  read-only
    STATUS  current
    DESCRIPTION
        "The value in seconds that all bridges use for ForwardDelay when this 
         bridge is acting as the root."
    ::= { cistGeneralInfo 11 }

cistMaxHopCount OBJECT-TYPE
    SYNTAX  INTEGER  (4..60)
    MAX-ACCESS  read-only
    STATUS  current
    DESCRIPTION
        "Indicates the maximum hop count value."
    ::= { cistGeneralInfo 12 }

mstpDigest OBJECT-TYPE
    SYNTAX  DisplayString (SIZE(0..63))
    MAX-ACCESS  read-only
    STATUS  current
    DESCRIPTION
        "The digest of the mstp."
    ::= { cistGeneralInfo 13 }

-- CIST Port Information Table
cistInfoPortTable OBJECT-TYPE
    SYNTAX SEQUENCE OF CistInfoPortTableEntry
    MAX-ACCESS not-accessible
    STATUS current
    DESCRIPTION
        "The table of CIST Port information."
    ::= { cistInfo 2 }

cistInfoPortTableEntry OBJECT-TYPE
    SYNTAX CistInfoPortTableEntry
    MAX-ACCESS not-accessible
    STATUS current
    DESCRIPTION
        "Information about a particular CIST Port."
    INDEX { cistInfoPortIndex }
    ::= { cistInfoPortTable 1 }

CistInfoPortTableEntry ::= SEQUENCE {
    cistInfoPortIndex            Integer32,
    cistInfoPortPriority         Integer32,
    cistInfoPortPathCost         Integer32,
    cistInfoPortState            INTEGER,
    cistInfoPortRole             INTEGER,
    cistInfoPortDesignatedBridge BridgeId,
    cistInfoPortDesignatedPort   OCTET STRING,
    cistInfoPortLinkType         INTEGER,
    cistInfoPortHelloTime        INTEGER
    }

cistInfoPortIndex OBJECT-TYPE
    SYNTAX Integer32
    MAX-ACCESS read-only
    STATUS current
    DESCRIPTION
        "The port number of the port for which this entry contains spanning
         tree configuration."
    ::= { cistInfoPortTableEntry 1 }

cistInfoPortPriority OBJECT-TYPE
    SYNTAX Integer32
    MAX-ACCESS read-only
    STATUS current
    DESCRIPTION
        "The four most significant bits of the Port Identifier of the 
         Spanning Tree instance can be modified by setting this value."
    ::= { cistInfoPortTableEntry 2 }

cistInfoPortPathCost OBJECT-TYPE
    SYNTAX Integer32
    MAX-ACCESS read-only
    STATUS current
    DESCRIPTION
        "The contribution of this port to the path cost of paths towards 
         the CIST Root which include this port."
    ::= { cistInfoPortTableEntry 3 }

cistInfoPortState OBJECT-TYPE
    SYNTAX INTEGER {
        disabled (1),
        discarding (2),
        learning (4),
        forwarding (5)
        }
    MAX-ACCESS read-only
    STATUS current
    DESCRIPTION
        "Current state of the Port as defined by the Common    
         spanning tree protocol." 
    ::= { cistInfoPortTableEntry 4 }

cistInfoPortRole OBJECT-TYPE
    SYNTAX INTEGER {
        disabled(1),
        alternate(2),
        backup(3),
        root(4),
        designated(5),
        master(6),
        unknown(7)
        }
    MAX-ACCESS read-only
    STATUS current
    DESCRIPTION
          "Selected Port Role of the port for this spanning tree instance."
    ::= { cistInfoPortTableEntry 5 }

cistInfoPortDesignatedBridge OBJECT-TYPE
    SYNTAX  BridgeId
    MAX-ACCESS  read-only
    STATUS  current
    DESCRIPTION
        "The unique Bridge Identifier of the bridge which this port  
         considers to be the Designated Bridge for the port's segment."   
    ::= { cistInfoPortTableEntry 6 }

cistInfoPortDesignatedPort OBJECT-TYPE
    SYNTAX  OCTET STRING (SIZE (2))
    MAX-ACCESS  read-only
    STATUS  current
      DESCRIPTION
          "The Port identifier of the port on the Designated Bridge    
           for this port's segment."                                           
    ::= { cistInfoPortTableEntry 7 }

cistInfoPortLinkType OBJECT-TYPE
    SYNTAX INTEGER {
        p2p(1),
        shared(2),
        unknown(3)
        }
    MAX-ACCESS read-only
    STATUS current
    DESCRIPTION
        "The point-to-point status of the LAN segment attached 
         to this port.  A value of p2p (2) indicates that this port is being
         treated as if it is connected to a point-to-point link. 
         A value of shared(3) indicates that this port is being treated as 
         having a shared media connection."
    ::= { cistInfoPortTableEntry 8 }

cistInfoPortHelloTime OBJECT-TYPE
    SYNTAX  INTEGER (1..10)
    MAX-ACCESS  read-only
    STATUS  current
    DESCRIPTION
        "The amount of time between the transmission of Configuration Port 
         PDUs in seconds."
    ::= { cistInfoPortTableEntry 9 }


-- UFD
ufdCurCfgState        OBJECT-TYPE
    SYNTAX  INTEGER  {
    enabled(1),
    disabled(2)
    }
    MAX-ACCESS  read-only
    STATUS  current
    DESCRIPTION
        "Enable or disable UFD state"
    ::= { ufdGeneralCfg 1 }

ufdNewCfgState OBJECT-TYPE
    SYNTAX  INTEGER  {
        enabled(1),
        disabled(2)
        }
    MAX-ACCESS  read-write
    STATUS  current
    DESCRIPTION
        "Enable or disable UFD state"
    ::= { ufdGeneralCfg 2 }


ufdCurCfgLtMPorts      OBJECT-TYPE
    SYNTAX  OCTET STRING
    MAX-ACCESS  read-only
    STATUS  current
    DESCRIPTION
        "The LtM port list. The ports are presented in bitmap format.
         in receiving order:

              OCTET 1  OCTET 2  .....
             xxxxxxxx xxxxxxxx .....
             ||    || |_ port 8
             ||    ||
             ||    ||___ port 7
             ||    |____ port 6
             ||      .    .   .
             ||_________ port 1
             |__________ reserved

         where x : 1 - The represented port belongs to LtM
            0 - The represented port does not belong to LtM"
    ::= { ufdGeneralCfg 3 }

ufdNewCfgLtMPorts      OBJECT-TYPE
    SYNTAX  OCTET STRING
    MAX-ACCESS  read-write
    STATUS  current
    DESCRIPTION
        "The LtM port list. The ports are presented in bitmap format.
         in receiving order:

              OCTET 1  OCTET 2  .....
             xxxxxxxx xxxxxxxx .....
             ||    || |_ port 8
             ||    ||
             ||    ||___ port 7
             ||    |____ port 6
             ||      .    .   .
             ||_________ port 1
             |__________ reserved

         where x : 1 - The represented port belongs to LtM
            0 - The represented port does not belong to LtM"
    ::= { ufdGeneralCfg 4 }


ufdCurCfgLtMTrunks      OBJECT-TYPE
    SYNTAX  OCTET STRING
    MAX-ACCESS  read-only
    STATUS  current
    DESCRIPTION
        "The LtM trunk list. The trunks are presented in bitmap format.
         in receiving order:

              OCTET 1  OCTET 2  .....
             xxxxxxxx xxxxxxxx .....
             ||    || |_ trunk 8
             ||    ||
             ||    ||___ trunk 7
             ||    |____ trunk 6
             ||      .    .   .
             ||_________ trunk 1
             |__________ reserved

         where x : 1 - The represented trunk belongs to LtM
            0 - The represented trunk does not belong to LtM"
    ::= { ufdGeneralCfg 5 }

ufdNewCfgLtMTrunks      OBJECT-TYPE
    SYNTAX  OCTET STRING
    MAX-ACCESS  read-write
    STATUS  current
    DESCRIPTION
        "The LtM trunk list. The trunks are presented in bitmap format.
         in receiving order:

              OCTET 1  OCTET 2  .....
             xxxxxxxx xxxxxxxx .....
             ||    || |_ trunk 8
             ||    ||
             ||    ||___ trunk 7
             ||    |____ trunk 6
             ||      .    .   .
             ||_________ trunk 1
             |__________ reserved

         where x : 1 - The represented trunk belongs to LtM
            0 - The represented trunk does not belong to LtM"
    ::= { ufdGeneralCfg 6 }



ufdCurCfgLtDPorts      OBJECT-TYPE
    SYNTAX  OCTET STRING
    MAX-ACCESS  read-only
    STATUS  current
    DESCRIPTION
        "The LtD port list. The ports are presented in bitmap format.
         in receiving order:

              OCTET 1  OCTET 2  .....
             xxxxxxxx xxxxxxxx .....
             ||    || |_ port 8
             ||    ||
             ||    ||___ port 7
             ||    |____ port 6
             ||      .    .   .
             ||_________ port 1
             |__________ reserved

         where x : 1 - The represented port belongs to LtD
            0 - The represented port does not belong to LtD"
    ::= { ufdGeneralCfg 7 }

ufdNewCfgLtDPorts      OBJECT-TYPE
    SYNTAX  OCTET STRING
    MAX-ACCESS  read-write
    STATUS  current
    DESCRIPTION
        "The LtD port list. The ports are presented in bitmap format.
         in receiving order:

              OCTET 1  OCTET 2  .....
             xxxxxxxx xxxxxxxx .....
             ||    || |_ port 8
             ||    ||
             ||    ||___ port 7
             ||    |____ port 6
             ||      .    .   .
             ||_________ port 1
             |__________ reserved

         where x : 1 - The represented port belongs to LtD
            0 - The represented port does not belong to LtD"
    ::= { ufdGeneralCfg 8 }


ufdCurCfgLtDTrunks      OBJECT-TYPE
    SYNTAX  OCTET STRING
    MAX-ACCESS  read-only
    STATUS  current
    DESCRIPTION
        "The LtD trunk list. The trunks are presented in bitmap format.
         in receiving order:

              OCTET 1  OCTET 2  .....
             xxxxxxxx xxxxxxxx .....
             ||    || |_ trunk 8
             ||    ||
             ||    ||___ trunk 7
             ||    |____ trunk 6
             ||      .    .   .
             ||_________ trunk 1
             |__________ reserved

         where x : 1 - The represented trunk belongs to LtD
            0 - The represented trunk does not belong to LtD"
    ::= { ufdGeneralCfg 9 }

ufdNewCfgLtDTrunks      OBJECT-TYPE
    SYNTAX  OCTET STRING
    MAX-ACCESS  read-write
    STATUS  current
    DESCRIPTION
        "The LtD trunk list. The trunks are presented in bitmap format.
         in receiving order:

              OCTET 1  OCTET 2  .....
             xxxxxxxx xxxxxxxx .....
             ||    || |_ trunk 8
             ||    ||
             ||    ||___ trunk 7
             ||    |____ trunk 6
             ||      .    .   .
             ||_________ trunk 1
             |__________ reserved

         where x : 1 - The represented trunk belongs to LtD
            0 - The represented trunk does not belong to LtD"
    ::= { ufdGeneralCfg 10 }

ufdNewCfgAddLtMPort OBJECT-TYPE
    SYNTAX  INTEGER
    MAX-ACCESS  read-write
    STATUS  current
    DESCRIPTION
        "The port to be added to LtM.  A '0' value is
         returned when read."
    ::= { ufdGeneralCfg 11 }

ufdNewCfgRemoveLtMPort OBJECT-TYPE
    SYNTAX  INTEGER
    MAX-ACCESS  read-write
    STATUS  current
    DESCRIPTION
        "The port to be removed from LtM.  A '0'
         value is returned when read."
    ::= { ufdGeneralCfg 12 }

ufdNewCfgAddLtMTrunk OBJECT-TYPE
    SYNTAX  INTEGER
    MAX-ACCESS  read-write
    STATUS  current
    DESCRIPTION
        "The trunk to be added to LtM.  A '0' value is
         returned when read."
    ::= { ufdGeneralCfg 13 }

ufdNewCfgRemoveLtMTrunk OBJECT-TYPE
    SYNTAX  INTEGER
    MAX-ACCESS  read-write
    STATUS  current
    DESCRIPTION
        "The trunk to be removed from LtM.  A '0'
         value is returned when read."
    ::= { ufdGeneralCfg 14 }


ufdNewCfgAddLtDPort OBJECT-TYPE
    SYNTAX  INTEGER
    MAX-ACCESS  read-write
    STATUS  current
    DESCRIPTION
        "The port to be added to LtD.  A '0' value is
         returned when read."
    ::= { ufdGeneralCfg 15}

ufdNewCfgRemoveLtDPort OBJECT-TYPE
    SYNTAX  INTEGER
    MAX-ACCESS  read-write
    STATUS  current
    DESCRIPTION
        "The port to be removed from LtM.  A '0'
         value is returned when read."
    ::= { ufdGeneralCfg 16 }

ufdNewCfgAddLtDTrunk OBJECT-TYPE
    SYNTAX  INTEGER
    MAX-ACCESS  read-write
    STATUS  current
    DESCRIPTION
        "The trunk to be added to LtM.  A '0' value is
         returned when read."
    ::= { ufdGeneralCfg 17 }

ufdNewCfgRemoveLtDTrunk OBJECT-TYPE
    SYNTAX  INTEGER
    MAX-ACCESS  read-write
    STATUS  current
    DESCRIPTION
        "The trunk to be removed from LtD.  A '0'
         value is returned when read."
    ::= { ufdGeneralCfg 18 }

ufdCurCfgGlobalState        OBJECT-TYPE
    SYNTAX  INTEGER  {
    enabled(1),
    disabled(2)
    }
    MAX-ACCESS  read-only
    STATUS  current
    DESCRIPTION
        "Current global Failover settings."
    ::= { ufdGeneralCfg 19 }

ufdNewCfgGlobalState OBJECT-TYPE
    SYNTAX  INTEGER  {
        enabled(1),
        disabled(2)
        }
    MAX-ACCESS  read-write
    STATUS  current
    DESCRIPTION
        "New global Failover settings."
    ::= { ufdGeneralCfg 20 }





-- FDB
fdbCurCfgAgingTime  OBJECT-TYPE
    SYNTAX   Integer32
    MAX-ACCESS  read-only
    STATUS  current
    DESCRIPTION
        "Fdb current aging time"
    ::= { fdbGeneralCfg 1 }

fdbNewCfgAgingTime OBJECT-TYPE
    SYNTAX   Integer32
    MAX-ACCESS  read-write
    STATUS  current
    DESCRIPTION
        "Fdb new aging time."
    ::= { fdbGeneralCfg 2 }

fdbNewCfgStaticTable OBJECT-TYPE
    SYNTAX  SEQUENCE OF FdbNewCfgStaticEntry
    MAX-ACCESS  not-accessible
    STATUS  current
    DESCRIPTION
        "The table of FDB static entries."
    ::= { fdb 2 }

fdbNewCfgStaticEntry OBJECT-TYPE
    SYNTAX  FdbNewCfgStaticEntry
    MAX-ACCESS  not-accessible
    STATUS  current
    DESCRIPTION
        "A row in the fdb table."
    INDEX   { fdbNewCfgEntryIndex }
    ::= { fdbNewCfgStaticTable 1 }

FdbNewCfgStaticEntry ::= SEQUENCE {
    fdbNewCfgEntryIndex			Integer32,
    fdbNewCfgAddVlan	                Integer32,
    fdbNewCfgAddPort	                Integer32,
    fdbNewCfgAddMac			PhysAddress,
    fdbNewCfgDelStaticEntry		INTEGER
    }

fdbNewCfgEntryIndex OBJECT-TYPE 
    SYNTAX  Integer32 
    MAX-ACCESS  read-only 
    STATUS  current 
    DESCRIPTION 
        "The fdb entry index" 
    ::= { fdbNewCfgStaticEntry 1 }

fdbNewCfgAddVlan OBJECT-TYPE 
    SYNTAX  Integer32 
    MAX-ACCESS  read-create
    STATUS  current 
    DESCRIPTION 
        "Add vlan for fdb entry index" 
    ::= { fdbNewCfgStaticEntry 2 }

fdbNewCfgAddPort OBJECT-TYPE
    SYNTAX  Integer32
    MAX-ACCESS   read-create
    STATUS  current
    DESCRIPTION
        "The MAC address port number." 
    ::= { fdbNewCfgStaticEntry 3 }

fdbNewCfgAddMac OBJECT-TYPE
    SYNTAX  PhysAddress
    MAX-ACCESS  read-create
    STATUS  current
    DESCRIPTION
        "Add a fdb entry."
    ::= { fdbNewCfgStaticEntry 4 }

fdbNewCfgDelStaticEntry OBJECT-TYPE
    SYNTAX  INTEGER {
        other(1),
        delete(2)
        }
    MAX-ACCESS  read-create
    STATUS  current
    DESCRIPTION
        "When set to the value of 2 (delete), the entire row is deleted.
         When read, other(1) is returned. Setting the value to anything
         other than 2(delete) has no effect on the state of the row."
    ::= { fdbNewCfgStaticEntry 5 }



-- General Information

generalInfoStpUplinkFast OBJECT-TYPE
    SYNTAX  INTEGER  {
        enabled(1),
        disabled(2)
        }
    MAX-ACCESS  read-only
    STATUS  current
    DESCRIPTION
        "STP uplink fast mode"
    ::= { genInfo 1 }

generalInfoUplinkFastRate OBJECT-TYPE
    SYNTAX  INTEGER 
    MAX-ACCESS  read-only
    STATUS  current
    DESCRIPTION
        "STP fast uplink rate."
    ::= { genInfo 2 }

-- VLAN information

vlanInfoTable OBJECT-TYPE
    SYNTAX SEQUENCE OF VlanInfoTableEntry
    MAX-ACCESS not-accessible
    STATUS current
    DESCRIPTION
        "The table of VLAN information."
    ::= { vlanInfo 1 }

vlanInfoTableEntry OBJECT-TYPE
    SYNTAX VlanInfoTableEntry
    MAX-ACCESS not-accessible
    STATUS current
    DESCRIPTION
        "Information about a particular VLAN."
    INDEX { vlanInfoId }
    ::= { vlanInfoTable 1 }

VlanInfoTableEntry ::= SEQUENCE {
    vlanInfoId                INTEGER,
    vlanInfoName              DisplayString,
    vlanInfoStatus            INTEGER,
    vlanInfoPorts             OCTET STRING
    }

vlanInfoId OBJECT-TYPE
    SYNTAX  INTEGER  (1..4095)
    MAX-ACCESS read-only
    STATUS current
    DESCRIPTION
        "The VLAN identifier."
    ::= { vlanInfoTableEntry 1 }

vlanInfoName OBJECT-TYPE
    SYNTAX  DisplayString (SIZE(0..32))
    MAX-ACCESS  read-only
    STATUS  current
    DESCRIPTION
        "The VLAN name."
    ::= { vlanInfoTableEntry 2 }

vlanInfoStatus OBJECT-TYPE
    SYNTAX  INTEGER  {
        enabled(2),
        disabled(3)
        }
    MAX-ACCESS  read-only
    STATUS  current
    DESCRIPTION
        "Enable or disable, VLAN state information"
    ::= { vlanInfoTableEntry 3 }

vlanInfoPorts OBJECT-TYPE
    SYNTAX  OCTET STRING
    MAX-ACCESS  read-only
    STATUS  current
    DESCRIPTION
        "The port list information in the VLAN. The ports are presented 
         in bitmap format.
         in receiving order:

             OCTET 1  OCTET 2  .....
             xxxxxxxx xxxxxxxx ..... 
             ||    || |_ port 8
             ||    ||  
             ||    ||___ port 7
             ||    |____ port 6
             ||      .    .   .
             ||_________ port 1
             |__________ reserved

         where x : 1 - The represented port belongs to the VLAN
                   0 - The represented port does not belong to the VLAN"
    ::= { vlanInfoTableEntry 4 }


-- Trunk Group Information

trunkGroupInfoTable OBJECT-TYPE
    SYNTAX SEQUENCE OF TrunkGroupInfoTableEntry
    MAX-ACCESS not-accessible
    STATUS current
    DESCRIPTION
        "The table of trunk group information."
    ::= { trunkGroupInfo 1 }

trunkGroupInfoTableEntry OBJECT-TYPE
    SYNTAX TrunkGroupInfoTableEntry
    MAX-ACCESS not-accessible
    STATUS current
    DESCRIPTION
        "A row in trunk group information table."
    INDEX { trunkGroupInfoIndex }
    ::= { trunkGroupInfoTable 1 }

TrunkGroupInfoTableEntry ::= SEQUENCE {
    trunkGroupInfoIndex       Integer32,
    trunkGroupInfoState       INTEGER,
    trunkGroupInfoPorts       OCTET STRING
    }

trunkGroupInfoIndex OBJECT-TYPE
    SYNTAX  Integer32  
    MAX-ACCESS  read-only
    STATUS  current
    DESCRIPTION
        "The identifier of the trunk group."
    ::= { trunkGroupInfoTableEntry 1 }

trunkGroupInfoState OBJECT-TYPE
    SYNTAX  INTEGER  {
        enabled(1),
        disabled(2)
        }
    MAX-ACCESS  read-only
    STATUS  current
    DESCRIPTION
        "Trunk group state."
    ::= { trunkGroupInfoTableEntry 2 }

trunkGroupInfoPorts OBJECT-TYPE
    SYNTAX  OCTET STRING
    MAX-ACCESS  read-only
    STATUS  current
    DESCRIPTION
        "The port list in the trunk group. The ports are presented in 
         bitmap format.
 
         in receiving order:
 
             OCTET 1  OCTET 2  .....
             xxxxxxxx xxxxxxxx ..... 
             ||    || |_ port 8
             ||    ||  
             ||    ||___ port 7
             ||    |____ port 6
             ||      .    .   .
             ||_________ port 1
             |__________ reserved

         where x : 1 - The represented port belongs to the trunk group
                   0 - The represented port does not belong to the trunk group"
    ::= { trunkGroupInfoTableEntry 3 }

 END
