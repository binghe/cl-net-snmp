-- *******************************************************************
-- CISCO-LWAPP-WLAN-MIB.my 
-- This MIB helps to manage the WLANs on the controller 
-- January 2006, Devesh Pujari, Prasanna Viswakumar
--
-- Copyright (c) 2006, 2007 by Cisco Systems, Inc.
-- All rights reserved.
-- *******************************************************************
--
CISCO-LWAPP-WLAN-MIB DEFINITIONS ::= BEGIN

IMPORTS 
        MODULE-IDENTITY, 
        OBJECT-TYPE,
        Unsigned32
                FROM SNMPv2-SMI
        MODULE-COMPLIANCE, 
        OBJECT-GROUP
                FROM SNMPv2-CONF
        TimeStamp,
	    TruthValue,
        RowStatus,
        DisplayString,
        StorageType
                FROM SNMPv2-TC
        SnmpAdminString
                FROM SNMP-FRAMEWORK-MIB
        ciscoMgmt
                FROM CISCO-SMI;

ciscoLwappWlanMIB      MODULE-IDENTITY
        LAST-UPDATED   "2007020300Z"
        ORGANIZATION   "Cisco Systems Inc."
        CONTACT-INFO  
               "        Cisco Systems,
                        Customer Service
                Postal: 170 West Tasman Drive
                        San Jose, CA  95134
                        USA
                   Tel: +1 800 553-NETS
      
                 Email: cs-wnbu-snmp@cisco.com"

        DESCRIPTION             
                "This MIB is intended to be implemented on all those
                devices operating as Central Controllers (CC)  that
                terminate the Light Weight Access Point Protocol
                tunnel from Cisco Light-weight LWAPP Access Points.

                This MIB helps to manage the WLANs on the controller.

                The relationship between CC and the LWAPP APs
                can be depicted as follows:

        +......+     +......+     +......+           +......+
        +      +     +      +     +      +           +      +
        +  CC  +     +  CC  +     +  CC  +           +  CC  +
        +      +     +      +     +      +           +      +
        +......+     +......+     +......+           +......+
          ..            .             .                 .
          ..            .             .                 .
         .  .            .             .                 .
        .    .            .             .                 .
       .      .            .             .                 .
      .        .            .             .                 .
   +......+ +......+     +......+      +......+          +......+
   +      + +      +     +      +      +      +          +      +
   +  AP  + +  AP  +     +  AP  +      +  AP  +          +  AP  +
   +      + +      +     +      +      +      +          +      +
   +......+ +......+     +......+      +......+          +......+
              .              .             .                 .
            .  .              .             .                 .
           .    .              .             .                 .
          .      .              .             .                 .
         .        .              .             .                 .
      +......+ +......+     +......+      +......+          +......+
      +      + +      +     +      +      +      +          +      +
      +  MN  + +  MN  +     +  MN  +      +  MN  +          +  MN  +
      +      + +      +     +      +      +      +          +      +
      +......+ +......+     +......+      +......+          +......+

                The LWAPP tunnel exists between the controller and
                the APs.  The MNs communicate with the APs through
                the protocol defined by the 802.11 standard.

                LWAPP APs, upon bootup, discover and join one of the
                controllers and the controller pushes the configuration,
                that includes the WLAN parameters, to the LWAPP APs.
                The APs then encapsulate all the 802.11 frames from
                wireless clients inside LWAPP frames and forward
                the LWAPP frames to the controller.
               
                                   GLOSSARY

                Access Point ( AP )

                An entity that contains an 802.11 medium access
                control ( MAC ) and physical layer ( PHY ) interface
                and provides access to the distribution services via
                the wireless medium for associated clients.  

                LWAPP APs encapsulate all the 802.11 frames in
                LWAPP frames and sends it to the controller to which
                it is logically connected to.

                Central Controller ( CC )

                The central entity that terminates the LWAPP protocol
                tunnel from the LWAPP APs.  Throughout this MIB,
                this entity also referred to as 'controller'.

                Light Weight Access Point Protocol ( LWAPP ) 

                This is a generic protocol that defines the
                communication between the Access Points and the
                controllers.

                Mobile Node ( MN )

                A roaming 802.11 wireless device in a wireless
                network associated with an access point. 

                Access Control List ( ACL )

                A list of rules used to restrict the traffic reaching 
                an interface or the CPU or WLAN.  Each ACL is an ordered 
                set of rules and actions.  If a rule matches then the 
                action for that rule is applied to the packet.

                802.1x

                The IEEE ratified standard for enforcing port based
                access control.  This was originally intended for
                use on wired LANs and later extended for use in
                802.11 WLAN environments.  This defines an
                architecture with three main parts - a supplicant
                (Ex. an 802.11 wireless client), an authenticator
                (the AP) and an authentication server(a Radius
                server).  The authenticator passes messages back
                and forth between the supplicant and the
                authentication server to enable the supplicant
                get authenticated to the network.

                Temporal Key Integrity Protocol ( TKIP )

                A security protocol defined to enhance the limitations
                of WEP.  Message Integrity Check and per-packet keying
                on all WEP-encrypted frames are two significant
                enhancements provided by TKIP to WEP.


                Cisco Key Integrity Protocol ( CKIP )

                A proprietary implementation similar to TKIP.  CKIP
                implements key permutation for protecting the CKIP
                key against attacks.  Other features of CKIP include
                expansion of encryption key to 16 bytes of length for
                key protection and MIC to ensure data integrity.


                Wired Equivalent Privacy ( WEP )

                A security method defined by 802.11. WEP uses a
                symmetric key stream cipher called RC4 to encrypt the
                data packets.

                Wi-Fi Protected Access ( WPA )

                Wi-Fi Protected Access (WPA and WPA2) are security
                systems created in response to several serious
                weaknesses found in Wired Equivalent Privacy (WEP).
                WPA implements the majority of the IEEE 802.11i
                standard, and was intended as an intermediate
                measure to take the place of WEP while 802.11i was
                prepared. WPA is designed to work with all wireless
                network interface cards, but not necessarily with
                first generation wireless access points.

                WLAN Layer 2 Security
                 
                WLAN layer 2 (MAC) security defines the encryption and 
                authentication approaches such as 802.1x, WPA, 
                WPA2, CKIP and WEP.                

                Delivery Traffic Indication Map ( DTIM )

                DTIM is measured in beacon intervals and is the time 
                period during which multicast/broadcast packets are
                sent to clients. This helps client to go in Power Saving
                mode and helps to save battery power.
 
                REFERENCE
 
                [1] Wireless LAN Medium Access Control ( MAC ) and
                Physical Layer ( PHY ) Specifications.

                [2] Draft-obara-capwap-lwapp-00.txt, IETF Light 
                Weight Access Point Protocol 

                [3] IEEE 802.11 - The original 1 Mbit/s and 2 Mbit/s, 
                2.4 GHz RF and IR standard."
        
        REVISION      "200702030000Z"
        DESCRIPTION
                "Added following objects in cLWlanConfigTable:  
                      cLWlanProfileName
                      cLWlanSsid 
                      cLWlanDiagChan
                      cLWlanStorageType
                 Added following table:
                      cLWlanConfigClientTable  
                 Added the following OBJECT-GROUPs:
                      ciscoLwappWlanConfigGroupSup1 
                      ciscoLwappWlanConfigClientGroup 
                 Added ciscoLwappWlanMIBComplianceRev1 MODULE-COMPLIANCE."
        REVISION      "200603210000Z"
        DESCRIPTION
                "Initial version of this MIB module. "
	REVISION      "200704020000Z" 	 
         DESCRIPTION 	 
                 "Added following object in cLWlanConfigClientTable 	 
                       cLWlanP2PBlocking "
        ::= { ciscoMgmt 512 }

ciscoLwappWlanMIBNotifs  OBJECT IDENTIFIER ::= { ciscoLwappWlanMIB 0 }
ciscoLwappWlanMIBObjects OBJECT IDENTIFIER ::= { ciscoLwappWlanMIB 1 }
ciscoLwappWlanMIBConform OBJECT IDENTIFIER ::= { ciscoLwappWlanMIB 2 }

ciscoLwappWlanConfig OBJECT IDENTIFIER  
        ::= { ciscoLwappWlanMIBObjects 1 }

ciscoLwappAPGroupsVlanConfig OBJECT IDENTIFIER
	::= { ciscoLwappWlanMIBObjects 2 }


ciscoLwappWlan11uConfig OBJECT IDENTIFIER
        ::= { ciscoLwappWlanMIBObjects 3 }

-- ********************************************************************
-- WLAN configuration
-- ********************************************************************

cLWlanConfigTable OBJECT-TYPE
        SYNTAX     SEQUENCE OF CLWlanConfigEntry
        MAX-ACCESS not-accessible
        STATUS     current
        DESCRIPTION
                "This table represents the WLAN configuration sent by
                the controller to the LWAPP APs for their operation.

                LWAPP APs exchange configuration messages with the
                controller and get the required configuration for
                their 802.11 related operations.  As part of these
                messages, the WLAN configuration is pushed by the
                controller to the LWAPP APs.  

                This table doesn't have any dependencies on other
                existing tables.  By defining cLWlanIndex, the
                unique identifier for a WLAN, this table provides
                a common index structure for use in several other
                new tables that populate information on security
                related attributes like authentication, encryption,
                802.11 parameters, Quality-of-Service attributes
                etc., that would relate to a particular WLAN.

                Rows are added or deleted by explicit 
                management actions initiated by the user from a
                network management station through the 
                cLWlanRowStatus object. " 
        ::= { ciscoLwappWlanConfig 1 }

cLWlanConfigEntry OBJECT-TYPE
        SYNTAX     CLWlanConfigEntry
        MAX-ACCESS not-accessible
        STATUS     current
        DESCRIPTION
                "Each entry in this table represents the WLAN
                configuration sent by the controller to LWAPP APs
                for use during their operations. entries can be added/deleted by explicit management actions by NMS or by user console"
        INDEX   { cLWlanIndex }
        ::= { cLWlanConfigTable 1 }

CLWlanConfigEntry ::= 
        SEQUENCE {
                cLWlanIndex               Unsigned32,  
                cLWlanRowStatus           RowStatus,
                cLWlanProfileName         SnmpAdminString,
                cLWlanSsid                OCTET STRING,
                cLWlanDiagChan            TruthValue,
                cLWlanStorageType         StorageType,
                cLWlanIsWired             TruthValue,
                cLWlanIngressInterface    OCTET STRING,
                cLWlanNACSupport          TruthValue,	
                cLWlanWepKeyChange        TimeStamp,
                cLWlanChdEnable           TruthValue,
                cLWlan802dot11anDTIM      Unsigned32,
                cLWlan802dot11bgnDTIM     Unsigned32,
		cLWlanLoadBalancingEnable TruthValue,
		cLWlanBandSelectEnable	  TruthValue,
		cLWlanPassiveClientEnable TruthValue,
		cLWlanReAnchorRoamedVoiceClientsEnable TruthValue
        }

cLWlanIndex OBJECT-TYPE
        SYNTAX     Unsigned32 (1..517)
        MAX-ACCESS not-accessible
        STATUS     current
        DESCRIPTION
                "This object uniquely identifies one instance of
                a WLAN on the controller. The value 513-517 indicates
                wired clients."
        ::= { cLWlanConfigEntry 1 }

cLWlanRowStatus OBJECT-TYPE
        SYNTAX     RowStatus
        MAX-ACCESS read-create
        STATUS     current
        DESCRIPTION
                "This is the status column for this row and used
                to create and delete specific instances of rows
                in this table.  
                The following objects are mandatory for successful
                creation of an entry:
                    cLWlanProfileName 
                    cLWlanSsid."
        ::= { cLWlanConfigEntry 2 }

cLWlanProfileName OBJECT-TYPE
        SYNTAX     SnmpAdminString (SIZE(1..64))
        MAX-ACCESS read-create
        STATUS     current
        DESCRIPTION
                "This object represents the profile name assigned 
                to this WLAN. The name assigned to a WLAN has to be 
                unique across all the WLANs on the controller.
                An administrator can assign a meaningful
                name that could be later used to refer a particular 
                WLAN on the controller.  This object cannot be 
                modified when cLWlanRowStatus is 'active'."
        ::= { cLWlanConfigEntry 3 }

cLWlanSsid OBJECT-TYPE
        SYNTAX     OCTET STRING (SIZE(1..32))
        MAX-ACCESS read-create
        STATUS     current
        DESCRIPTION
                "This object represents the SSID assigned to 
                this WLAN. The access points will broadcast this SSID 
                on this WLAN. Different WLAN could use the same SSID as
                long as the layer 2 security is different. This object 
                cannot be modified when cLWlanRowStatus is 'active'."
        ::= { cLWlanConfigEntry 4 }

cLWlanDiagChan OBJECT-TYPE
        SYNTAX     TruthValue
        MAX-ACCESS read-create
        STATUS     current
        DESCRIPTION
                "This object is used to configure this WLAN as a 
                 diagnostic WLAN. A value of 'true'  indicates that 
                 the diagnostic WLAN is enabled.  A value of 'false' 
                 indicates that the diagnostic WLAN is disabled."
        DEFVAL { false }
        ::= { cLWlanConfigEntry 5 }

cLWlanStorageType OBJECT-TYPE
        SYNTAX       StorageType
        MAX-ACCESS   read-create
        STATUS       current
        DESCRIPTION
                "This object represnts the storage type for this conceptual
                 row."
        DEFVAL { nonVolatile }
        ::= { cLWlanConfigEntry 6 }
        

cLWlanIsWired OBJECT-TYPE
        SYNTAX     TruthValue
        MAX-ACCESS read-create
        STATUS     current
        DESCRIPTION
                 "This object differentiates between a wired lan and
                  a wireless LAN. If set to true this LAN represents
                  a wired LAN."
        ::= { cLWlanConfigEntry 7 }

cLWlanIngressInterface OBJECT-TYPE
       SYNTAX     OCTET STRING (SIZE(0..32))
       MAX-ACCESS read-write
       STATUS     current
       DESCRIPTION
                "The ingress interface attached to the wireless lan."
       ::= { cLWlanConfigEntry 8 }

cLWlanNACSupport OBJECT-TYPE
        SYNTAX     TruthValue
        MAX-ACCESS read-write
        STATUS     current
        DESCRIPTION
                "This object is used to configure the NAC- Out Of Band(OOB)
                 support for the WLAN.
                 A value of 'true'  indicates that
                 the WLAN supports the NAC- Out Of Band(OOB) feature.  
                 A value of 'false' indicates that
                 the WLAN does not support the NAC- Out Of Band(OOB) feature."
        DEFVAL { false }
::= { cLWlanConfigEntry 9 }

cLWlanWepKeyChange OBJECT-TYPE
    SYNTAX       TimeStamp
    MAX-ACCESS   read-only
    STATUS       current
    DESCRIPTION
        "This object represents the time when the 
        static WEP key was changed by the user."
    ::= { cLWlanConfigEntry 10 }

cLWlanChdEnable OBJECT-TYPE
    SYNTAX       TruthValue
    MAX-ACCESS   read-write
    STATUS       current
    DESCRIPTION 
        "This object indicates whether Coverage Hole Detection 
        (CHD) is enabled on the controller. A value of 'true'
        indicates CHD is on and a value of 'false' indicates 
        CHD is truend off for this WLAN."
    DEFVAL { true }
    ::= { cLWlanConfigEntry 11 }

cLWlan802dot11anDTIM  OBJECT-TYPE
    SYNTAX     Unsigned32 (1..255)
    UNITS      "Beacon Intervals"
    MAX-ACCESS read-write
    STATUS     current
    DESCRIPTION
        "This object represents DTIM configuration per WLAN for each 
         802.11 network.  
         The DTIM value is measured in Beacon Intervals."     
    DEFVAL { 1 }
    ::= { cLWlanConfigEntry 12 }

cLWlan802dot11bgnDTIM  OBJECT-TYPE
    SYNTAX     Unsigned32 (1..255)
    UNITS      "Beacon Intervals"
    MAX-ACCESS read-write
    STATUS     current
    DESCRIPTION
        "This object represents DTIM configuration per WLAN for each 
         802.11 network.  
         The DTIM value is measured in Beacon Intervals."     
    DEFVAL { 1 }
    ::= { cLWlanConfigEntry 13 }

cLWlanLoadBalancingEnable OBJECT-TYPE
    SYNTAX       TruthValue
    MAX-ACCESS   read-write
    STATUS       current
    DESCRIPTION 
        "This object indicates whether Load Balancing is  
        enabled on the controller for this WLAN . A value of 'true'
        indicates Load Balance is on and a value of 'false' indicates 
        Load Balance is turned off for this WLAN."
    DEFVAL { true }
    ::= { cLWlanConfigEntry 14 }

cLWlanBandSelectEnable OBJECT-TYPE
    SYNTAX       TruthValue
    MAX-ACCESS   read-write
    STATUS       current
    DESCRIPTION 
        "This object indicates whether Band Select is enabled 
        on the controller for this WLAN. A value of 'true'
        indicates Band Select is on and a value of 'false' indicates 
        Band Select is turned off for this WLAN."
    DEFVAL { true }
    ::= { cLWlanConfigEntry 15 }

cLWlanPassiveClientEnable OBJECT-TYPE
    SYNTAX       TruthValue
    MAX-ACCESS   read-write
    STATUS       current
    DESCRIPTION
        "This object indicates whether passive client is enabled
        on the controller for this WLAN. A value of 'true'
        indicates passive client is on and a value of 'false' indicates
        passive client is turned off for this WLAN."
    DEFVAL { false }
    ::= { cLWlanConfigEntry 16 }

cLWlanReAnchorRoamedVoiceClientsEnable OBJECT-TYPE
    SYNTAX       TruthValue
    MAX-ACCESS   read-write
    STATUS       current
    DESCRIPTION
        "This object indicates whether the Roamed Voice Client Re-Anchoring
        feature is enabled on the controller for this WLAN. 
        A value of 'true' indicates the roamed voice clients will get 
        re-anchored,
        a value of 'false' indicates the roamed voice clients re-anchoring
        is turned off for this WLAN."
    DEFVAL { false }
    ::= { cLWlanConfigEntry 17 }
    
-- Start - Hiding 802.11u (Mobile Concierge) feature in J main branch

--********************************************************************
--*        WLAN 11u  Table
--********************************************************************
                                                                        
--cLWlan11uTable OBJECT-TYPE
--        SYNTAX     SEQUENCE OF CLWlan11uEntry
--        MAX-ACCESS not-accessible
--        STATUS     current
--        DESCRIPTION
--                "This table represents the generic 802.11u
--                 configuration for a particular WLAN in a
--                 controller."
--        ::= { ciscoLwappWlan11uConfig 1 }

--cLWlan11uEntry OBJECT-TYPE
--        SYNTAX     CLWlan11uEntry
--        MAX-ACCESS not-accessible
--        STATUS     current
--        DESCRIPTION
--                "Each entry in this table represents the generic 802.11u
--                 configuration for a WLAN."
--        INDEX   { cLWlanIndex }
--        ::= { cLWlan11uTable 1 }



--CLWlan11uEntry ::=
--        SEQUENCE {
--                cLWlan11uStatus            TruthValue,
--                cLWlan11uInternetAccess    TruthValue,
--                cLWlan11uNetworkType       INTEGER,
--                cLWlan11uVenueGroup        INTEGER,
--                cLWlan11uVenueType         INTEGER,
--                cLWlan11uVenueName         SnmpAdminString
--                 }

--cLWlan11uStatus   OBJECT-TYPE
--    SYNTAX       TruthValue
--    MAX-ACCESS   read-write
--    STATUS       current
--    DESCRIPTION
--        "This object is used to configure the 802.11u support
--         for this WLAN. A value of 'true' indicates that 802.11u
--         support is enabled for this WLAN and a  value of 'false' indicates
--         that the support  is disabled for this WLAN."
--    DEFVAL { false }
--    ::= { cLWlan11uEntry 1 }
--cLWlan11uInternetAccess    OBJECT-TYPE
--    SYNTAX       TruthValue
--    MAX-ACCESS   read-write
--    STATUS       current
--    DESCRIPTION
--        "This object is used to configure the internet access
--         with respect to 802.11u feature for this WLAN.
--         A value of 'true' indicates that internet access is
--         enabled for this WLAN and a  value of 'false' indicates
--         that the internet access  is disabled for this WLAN."
--    DEFVAL { true }
--    ::= { cLWlan11uEntry 2 }

--cLWlan11uNetworkType  OBJECT-TYPE
--        SYNTAX     INTEGER {
--                         invalid(1),
--                         private(2),
--                         privateWithGuestAccess(3),
--                         chargeablePublicNetwork(4),
--                         freePublicNetwork(5),
--                         testOrEquipment(6),
--                         wildcard(7)
--                   }
--        MAX-ACCESS read-write
--        STATUS     current
--        DESCRIPTION
--                "This object indicates the network type with respect
--                to  802.11u feature , for this WLAN."
--        DEFVAL  { private }
--        ::= { cLWlan11uEntry 3 }

--cLWlan11uVenueGroup   OBJECT-TYPE
--        SYNTAX     INTEGER {
--                            unspecified(1),
--                            assembly(2),
--                            business(3),
--                            educational(4),
--                            factoryAndIndustrial(5),
--                            institutional(6),
--                            mercantile(7),
--                            residential(8),
--                            storage(9),
--                            utilityAndMisc(10),
--                            vehicular(11),
--                            outdoor(12)
--                            }
--        MAX-ACCESS read-write
--        STATUS     current
--        DESCRIPTION
--                "This object indicates the venue group with respect
--            to 802.11u feature , for this WLAN."
--        DEFVAL  { unspecified }
--        ::= { cLWlan11uEntry 4 }


--cLWlan11uVenueType   OBJECT-TYPE
--        SYNTAX     INTEGER  {
--                      unspecified(1),
--                      unspecifiedAssembly(2),
--                      arena(3),
--                      stadium(4),
--                      passengerTerminal(5),
--                      amphitheater(6),
--                      amusementPark(7),
--                      placeOfWorship(8),
--                      conventionCenter(9),
--                      library(10),
--                      museum(11),
--                      restaurant(12),
--                      theater(13),
--                      bar(14),
--                      coffeeShop(15),
--                      zooOrAquarium(16),
--                      emergencyCoordinationCenter(17),
--                      unspecifiedBusiness(18),
--                      doctorOrDentistOffice(19),
--                      bank(20),
--                      fireStation(21),
--                      policeStation(22),
--                      postOffice(23),
--                      professionalOffice(24),
--                      researchAndDevelopmentFacility(25),
--                      attorneyOffice(26),
--                      unspecifiedEducational(27),
--                      schoolPrimary(28),
--                      schoolSecondary(29),
--                      universityOrCollege(30),
--                      unspecifiedFactoryAndIndustrial(31),
--                      factory(32),
--                      unspecifiedInstitutional(33),
--                      hospital(34),
--                      longTermCareFacility(35),
--                      alcoholAndDrugRehabilitationCenter(36),
--                      groupHome(37),
--                      prisonOrJail(38),
--                      unspecifiedMercantile(39),
--                      retailStore(40),
--                      groceryMarket(41),
--                      atomotiveServiceStation(42),
--                      unspecifiedResidential(43),
--                      hotelOrMotel(44),
--                      dormitory(45),
--                      boardingHouse(46),
--                      unspecifiedVehicular(47),
--                      automobileOrTruck(48),
--                      airplane(49),
--                      bus(50),
--                      ferry(51),
--                      shipOrBoat(52),
--                      train(53),
--                      unspecifiedOutdoor(54),
--                      muniMeshNetwork(55),
--                      cityPark(56)
--                     }
--        MAX-ACCESS read-write
--        STATUS     current
--        DESCRIPTION
--                "This object indicates the venue type within
--                a particular venue group, with respect
--                to  802.11u feature , for this WLAN.
--                The Venue group-Venue Type relationship is per
--                the following table."
--        DEFVAL  { unspecified }
--        ::= { cLWlan11uEntry 5 }

--cLWlan11uVenueName OBJECT-TYPE
--        SYNTAX     SnmpAdminString (SIZE(1..256))
--        MAX-ACCESS read-write
--        STATUS     current
--        DESCRIPTION
--                "This is the venue name defined for this WLAN.
--                with respect to  802.11u feature."

--        ::= { cLWlan11uEntry 6 }                        

--********************************************************************
--*        WLAN 11u OUI Table
--********************************************************************

--cLWlan11uOuiTable OBJECT-TYPE
--        SYNTAX     SEQUENCE OF CLWlan11uOuiEntry
--        MAX-ACCESS not-accessible
--        STATUS     current
--        DESCRIPTION
--                "This table represents the OUI
--                 (organizational unique identifier) 
--                 configuration for a particular WLAN.
--                 OUIs are assigned by IEEE.
--                 A WLAN can have up to 32 OUIs defined.
--                 OUI configuration per WLAN is required 
--                 for the 802.11u feature to work." 
--        ::= { ciscoLwappWlan11uConfig 2 }

--cLWlan11uOuiEntry OBJECT-TYPE
--        SYNTAX     CLWlan11uOuiEntry
--        MAX-ACCESS not-accessible
--        STATUS     current
--        DESCRIPTION
--                "Each entry in this table represents the OUI
--                 (organizational unique identifier) 
--                 configuration for a particular WLAN.
--                 OUIs are assigned by IEEE.
--                 A WLAN can have up to 32 OUIs defined.
--                 OUI configuration per WLAN is required 
--                 for the 802.11u feature to work."  
                 
--        INDEX   { cLWlanIndex,cLWlan11uOuiIndex }
--        ::= { cLWlan11uOuiTable 1 }

--CLWlan11uOuiEntry ::= 
--        SEQUENCE {
--                 cLWlan11uOuiIndex          Unsigned32,
--                 cLWlan11uOui               OCTET STRING,
--                 cLWlan11uOuiIsBeacon       TruthValue,
--                 cLWlan11uOuiRowStatus      RowStatus
--                 }          
             
            
--cLWlan11uOuiIndex OBJECT-TYPE
--        SYNTAX     Unsigned32 (1..32)
--        MAX-ACCESS read-create
--        STATUS     current
--        DESCRIPTION
--                 "This object uniquely identifies one instance of
--                  a OUI on a WLAN.Each WLAN can have up to 32 OUIs defined.
--                  Each OUI should be unique."
--        ::= { cLWlan11uOuiEntry 1 } 

--cLWlan11uOui      OBJECT-TYPE
--        SYNTAX     OCTET STRING (SIZE(6)) 
--        MAX-ACCESS read-create
--        STATUS     current
--        DESCRIPTION
--                "The OUI field is a public OUI assigned by the IEEE. 
--                 Each OUI identifies a roaming consortium 
--                 (group of SSPs with inter-SSP roaming agreement) 
--                 or a single SSP.WLAN can have up to 32 OUIs defined.
--                 Each OUI defined for a WLAN should be unique.
--                 For example the value for Cisco is 004096."
                                   
--        ::= { cLWlan11uOuiEntry 2 }  
                                    
--cLWlan11uOuiIsBeacon OBJECT-TYPE
--        SYNTAX     TruthValue
--        MAX-ACCESS read-create
--        STATUS     current
--        DESCRIPTION
--                "This object is used to configure this particular
--                 OUI as one of the beacon OUIs.
--                 Beacon can carry at most 3 OUIs.
--                 User should be able to select 0-3 OUIs 
--                 (from the already configured OUIs for this WLAN). 
--                 A value of 'true'  indicates that this OUI would 
--                 be carried in beacon.  A value of 'false' 
--                 indicates that this OUI is not a beacon OUI."
--        DEFVAL { false }
--        ::= { cLWlan11uOuiEntry 3 }

--cLWlan11uOuiRowStatus OBJECT-TYPE
--        SYNTAX     RowStatus
--        MAX-ACCESS read-create
--        STATUS     current
--        DESCRIPTION
--                 "Row Status for creation/deletion of a particular 
--                  OUI entry in the table."
--        ::= { cLWlan11uOuiEntry 4 }

-- End - Hiding 802.11u (Mobile Concierge) feature in J main branch

--********************************************************************
--*       AP Groups Vlan Config
--********************************************************************
cLAPGroupsVlanConfigTable OBJECT-TYPE
         SYNTAX SEQUENCE OF CLAPGroupsVlanConfigEntry
         MAX-ACCESS not-accessible
         STATUS current
         DESCRIPTION
                  "A table for the WLAN-interface-mappings and WLAN-NAC
                   settings allowed for each configured site.
                   Each site can have a set of WLANs associated
                   with it."
         ::= { ciscoLwappAPGroupsVlanConfig 1 }

cLAPGroupsVlanConfigEntry OBJECT-TYPE
         SYNTAX CLAPGroupsVlanConfigEntry
         MAX-ACCESS not-accessible
         STATUS current
         DESCRIPTION
                  "An entry in cLAPGroupsVlanMappingTable."
         INDEX { cLAPGroupName, cLWlanProfileName }
         ::= { cLAPGroupsVlanConfigTable 1 }

CLAPGroupsVlanConfigEntry ::=
         SEQUENCE {
                cLAPGroupName DisplayString,
                cLAPGroupsVlanMappingInterfaceName OCTET STRING,
                cLAPGroupNACSupport TruthValue,
                cLAPGroupsVlanConfigRowStatus RowStatus
         }

cLAPGroupName OBJECT-TYPE
        SYNTAX OCTET STRING (SIZE(1..32))
        MAX-ACCESS not-accessible
        STATUS current
        DESCRIPTION
                 "The string is an unique identifier/name assigned to a site."
        ::= { cLAPGroupsVlanConfigEntry 1}

cLAPGroupsVlanMappingInterfaceName OBJECT-TYPE
        SYNTAX OCTET STRING (SIZE(1..32))
        MAX-ACCESS read-create
        STATUS current
        DESCRIPTION
                "When an AP is associated with a site, and the site
                 has an associated set of WLANs, then only those WLANs are
                 beamed by the AP. Here 'cLAPGroupsVlanMappingInterfaceName'
                 is the interface to be used when a client connects to the
                 'cLWlanProfileName' WLAN on this AP."
    ::= { cLAPGroupsVlanConfigEntry 2}

cLAPGroupNACSupport OBJECT-TYPE
        SYNTAX  TruthValue
        MAX-ACCESS  read-create
        STATUS  current
        DESCRIPTION
                 "This object is used to configure the NAC- Out Of Band(OOB)
                  support for this AP groups VLAN.
                  A value of 'true'  indicates that
                  the AP group supports the NAC- Out Of Band(OOB) feature.  
                  A value of 'false' indicates that
                  the AP group does not support the NAC- Out Of Band(OOB) feature."
        DEFVAL { false }
        ::= { cLAPGroupsVlanConfigEntry 3 }

cLAPGroupsVlanConfigRowStatus  OBJECT-TYPE
      SYNTAX RowStatus
      MAX-ACCESS read-create
      STATUS current
      DESCRIPTION
           "Row Status for creation/deletion of WLAN-interface-mappings and NAC-OOB
            setting associated with sites."
      ::= { cLAPGroupsVlanConfigEntry 4 }

-- ********************************************************************
-- WLAN Client Configuration
-- ********************************************************************

cLWlanConfigClientTable OBJECT-TYPE
        SYNTAX     SEQUENCE OF CLWlanConfigClientEntry
        MAX-ACCESS not-accessible
        STATUS     current
        DESCRIPTION
                "This table represents the WLAN configuration for 
                 the 802.11 wireless clients that are associated 
                 with the APs that have joined this controller.

                The creation of a new row in cLWlanConfigTable,
                through an explicit network management action,
                results in creation of an entry in this table.
                Similarly, deletion of a row in
                cLWlanConfigTable through user action causes the
                deletion of corresponding row in this table.

                This table has an one-to-one relationship with
                cLWlanConfigTable. There exists an entry in this 
                table for each corresponding entry in the 
                cLWlanConfigTable."
        ::= { ciscoLwappWlanConfig 2 }

cLWlanConfigClientEntry OBJECT-TYPE
        SYNTAX     CLWlanConfigClientEntry
        MAX-ACCESS not-accessible
        STATUS     current
        DESCRIPTION
                "Each entry represents a conceptual row in this
                table and provides the information about the
                clients associated on the WLAN, uniquely identified by
                the cLWlanIndex." 

-- The following was converted from AUGMENTS to INDEX to separate
-- implementation and does not have any external impact
-- to users of MIB. The version available at mib-police page
-- will be shipped to the customers. This version is for
-- INTERNAL USE ONLY.
--      AUGMENTS {cLWlanConfigEntry }
        INDEX { cLWlanIndex }
        ::= { cLWlanConfigClientTable 1 }

CLWlanConfigClientEntry ::= 
        SEQUENCE {
                cLWlanClientAclName      DisplayString ,
                cLWlanP2PBlocking        INTEGER 
        }

cLWlanClientAclName OBJECT-TYPE
        SYNTAX     DisplayString (SIZE(0..64))
        MAX-ACCESS read-write
        STATUS     current
        DESCRIPTION
                "This object represents the name of the ACL applied 
                 to this WLAN.  If it is required to remove the ACL
                 name for a WLAN, it should be set to 'none'.
                 ACL's are applied in the following priority order - 
                 interfaces ACLs, WLAN ACLs, client ACLs."
        ::= { cLWlanConfigClientEntry 1 }

cLWlanP2PBlocking  OBJECT-TYPE 	 
         SYNTAX     INTEGER { 	 
                       disable(1), 	 
                       drop(2), 	 
                       forwardUp(3) 	 
                    } 	 
         MAX-ACCESS read-write 	 
         STATUS     current 	 
         DESCRIPTION 	 
                "This object represents per WLAN peer-to-peer 	 
                blocking behavior on controller. Peer-to-peer 	 
                blocking means traffic between two clients on 	 
                same VLAN will not be bridged. 	 
  	 
                    disable   : Peer-to-peer blocking is disabled 	 
                                and traffic is bridged locally 	 
                                within the controller. 	 
                    drop      : The packet will be discarded. 	 
                    forwardUp : The packet will be forwarded on the 	 
                                upstream VLAN. The device 'north' of 	 
                                the controller can then make the 	 
                                decision about what to do with the 	 
                                packet." 	 
         DEFVAL { disable } 	 
::=  { cLWlanConfigClientEntry 2 }

--********************************************************************
--*    Compliance statements  
--********************************************************************
ciscoLwappWlanMIBCompliances OBJECT IDENTIFIER
        ::= { ciscoLwappWlanMIBConform 1 }

ciscoLwappWlanMIBGroups OBJECT IDENTIFIER
        ::= { ciscoLwappWlanMIBConform 2 }

ciscoLwappWlanMIBCompliance MODULE-COMPLIANCE
        STATUS     deprecated 
        DESCRIPTION
                "The compliance statement for the SNMP entities that
                implement the ciscoLwappWlanMIB module. "
        MODULE MANDATORY-GROUPS {                
                ciscoLwappWlanConfigGroup
             }

                OBJECT  cLWlanRowStatus  
                SYNTAX  INTEGER {
                              active(1),
                              createAndGo(4),
                              destroy(6)
                        }
                DESCRIPTION
                        "An implementation is only required to support
                        three of the six enumerated values of the
                        RowStatus textual convention, specifically,
                        'active', 'createAndGo' and 'destroy'. "

        ::= { ciscoLwappWlanMIBCompliances 1 }

ciscoLwappWlanMIBComplianceRev1 MODULE-COMPLIANCE
        STATUS     current 
        DESCRIPTION
                "The compliance statement for the SNMP entities that
                implement the ciscoLwappWlanMIB module. "
        MODULE MANDATORY-GROUPS {                
                ciscoLwappWlanConfigGroupSup1,
                ciscoLwappWlanConfigClientGroup
             }

                OBJECT  cLWlanRowStatus  
                SYNTAX  INTEGER {
                              active(1),
                              createAndGo(4),
                              destroy(6)
                        }
                DESCRIPTION
                        "An implementation is only required to support
                        three of the six enumerated values of the
                        RowStatus textual convention, specifically,
                        'active', 'createAndGo' and 'destroy'. "

        ::= { ciscoLwappWlanMIBCompliances 2 }

--********************************************************************
--*    Units of conformance  
--********************************************************************

ciscoLwappWlanConfigGroup OBJECT-GROUP
        OBJECTS {
                cLWlanRowStatus
             }                
        STATUS     deprecated
        DESCRIPTION
                "This collection of objects represent the 
                configuration of WLANs on the controller to be passed
                to an LWAPP AP. "
        ::= { ciscoLwappWlanMIBGroups 1 }

ciscoLwappWlanConfigGroupSup1 OBJECT-GROUP
        OBJECTS {
                  cLWlanRowStatus,
                  cLWlanProfileName,
                  cLWlanSsid, 
                  cLWlanDiagChan,
                  cLWlanStorageType
             }                
        STATUS     current
        DESCRIPTION
                "This collection of objects represent the 
                configuration of WLANs on the controller to be passed
                to an LWAPP AP. "
        ::= { ciscoLwappWlanMIBGroups 2 }

ciscoLwappWlanConfigClientGroup OBJECT-GROUP
        OBJECTS {
                  cLWlanClientAclName
             }                
        STATUS     current
        DESCRIPTION
                "This collection of objects represent the 
                configuration of WLANs on the controller to be passed
                to an 8021.11 clients. "
        ::= { ciscoLwappWlanMIBGroups 3 }


--********************************************************************
--*   End of units of conformance  
--********************************************************************

END
