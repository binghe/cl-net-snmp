-- ****************************************************************************
-- :CPQ,DEV:
--
-- * COMPAQ HOST OS RELATED INFORMATION SNMP MIB DEFINITIONS
--
-- * $Date: 2003/06/10 23:27:27 $
-- * $Revision: 1.1 $
--
-- Compaq Computer Corporation
-- Confidential - Need To Know
-- ****************************************************************************
-- :CPQ,ENDDEV:
--
--                  Host Operating System Information
--         Management Information Base for SNMP Network Management
--
--
--      Copyright 1997, Compaq Computer Corporation.
--      All Rights Reserved.
--
--      The information in this document is subject to change without notice.
--
--      COMPAQ COMPUTER CORPORATION SHALL NOT BE LIABLE FOR TECHNICAL
--      OR EDITORIAL ERRORS OR OMISSIONS CONATINED HEREIN; NOR FOR INCIDENTAL
--      OR CONSEQUENTIAL DAMAGES RESULTING FROM THE FURNISHING, PERFORMANCE,
--      OR USE OF THIS MATERIAL.
--
--      Refer to the READMIB.RDM file for more information about the
--      organization of the information in the Compaq Enterprise.
--
--      The Host OS MIB provides operating system information, such as
--      name, version, file system information, software running, and more.
--
--      The Compaq Enterprise number is 232.
--      The ASN.1 prefix to, and including the Compaq Enterprise is:
--           1.3.6.1.4.1.232
--
-- ****************************************************************************













































































































































































































































































































































































































































































































































































































































































































































































































































































































































































































































































































































































































































































































































































CPQHOST2-MIB DEFINITIONS ::= BEGIN

    IMPORTS
        enterprises             FROM RFC1155-SMI
        Counter                 FROM RFC1155-SMI
        DisplayString           FROM RFC1213-MIB
        OBJECT-TYPE             FROM RFC-1212
        TRAP-TYPE               FROM RFC-1215
        sysName                 FROM RFC1213-MIB;

    compaq              OBJECT IDENTIFIER ::= { enterprises 232 }
    cpqHostOs           OBJECT IDENTIFIER ::= { compaq 11 }
    cpqHoComponent      OBJECT IDENTIFIER ::= { cpqHostOs 2 }

    cpqHoClients        OBJECT IDENTIFIER ::= { cpqHoComponent 12 }


-- ****************************************************************************
--   OS Client Table
--   ====================
--
-- The compaq enterprise              (1.3.6.1.4.1.232)
--      cpqHostOS Group               (1.3.6.1.4.1.232.11)
--       cpqHoComponent Group         (1.3.6.1.4.1.232.11.2)
---       cpqHoClient Group           (1.3.6.1.4.1.232.11.2.12)
--
--      The cpqHoClient table contains entries describing identification,
--      address, and status information about each unit that is using
--      services provided by this unit.
--
-- ****************************************************************************



    cpqHoClientLastModified OBJECT-TYPE
        SYNTAX  OCTET STRING (SIZE (7))
        ACCESS  read-only
        STATUS  mandatory
        DESCRIPTION
            "The date/time of the last modification to the client table.

             field  octets  contents                  range
             =====  ======  =======                  =====
               1      1-2   year                      0..65536
               2       3    month                     1..12
               3       4    day                       1..31
               4       5    hour                      0..23
               5       6    minute                    0..59
               6       7    second                    0..60
                            (use 60 for leap-second)


            This field will be set to all 0's if there are no entries to the
            client table.

            The year field will be set to 0xFFFF if the agent does not support
            the client table.

            The year field is set with the most significant octect first."
-- :CPQ,DEV:
-- This variable must be supported by agents that support the Host MIB.
-- The table below is optional.  If an agent does not support the table,
-- the LastModified year value will be 0xFFFF.
-- :CPQ,ENDDEV:
        ::= { cpqHoClients 1 }

    cpqHoClientDelete OBJECT-TYPE
        SYNTAX DisplayString (SIZE (0..15))
        ACCESS read-write
        STATUS mandatory
        DESCRIPTION
        "Setting this variable to the name of a client in the client table
         will cause that row in the table to be deleted.  Any other set
         will fail.

         Note that the indices of the table will (most likely) be renumbered
         following a deletion."
        ::= { cpqHoClients 2 }


    cpqHoClientTable OBJECT-TYPE
        SYNTAX  SEQUENCE OF CpqHoClientEntry
        ACCESS  not-accessible
        STATUS  mandatory
        DESCRIPTION
            "A table of client descriptions."
        ::= { cpqHoClients 3 }

    cpqHoClientEntry OBJECT-TYPE
        SYNTAX  CpqHoClientEntry
        ACCESS  not-accessible
        STATUS  mandatory
        DESCRIPTION
            "A client description."
        INDEX   { cpqHoClientIndex }
        ::= { cpqHoClientTable 1 }

    CpqHoClientEntry ::= SEQUENCE {
        cpqHoClientIndex              INTEGER,
        cpqHoClientName               DisplayString,
        cpqHoClientIpxAddress         OCTET STRING,
        cpqHoClientIpAddress          IpAddress,
        cpqHoClientCommunity          DisplayString,
        cpqHoClientID                 OCTET STRING
    }

    cpqHoClientIndex OBJECT-TYPE
        SYNTAX  INTEGER (0..65535)
        ACCESS  read-only
        STATUS  mandatory
        DESCRIPTION
            "An index that uniquely specifies this entry."
        ::= { cpqHoClientEntry 1 }

    cpqHoClientName OBJECT-TYPE
        SYNTAX  DisplayString (SIZE (0..15))
        ACCESS  read-only
        STATUS  mandatory
        DESCRIPTION
            "The Win95 machine name of this client."

-- Note that Win95 limits the machine name to a maximum of 15 characters.

        ::= { cpqHoClientEntry 2 }

    cpqHoClientIpxAddress OBJECT-TYPE
        SYNTAX  OCTET STRING (SIZE (20))
        ACCESS  read-only
        STATUS  mandatory
        DESCRIPTION
            "The IPX address for this client, all octets should be set to
             0xff if this machine does not support IPX.

             The format is NetAddr:NodeNumber and sent in MSB order:

                                  1111111111
                       01234567:890123456789"

-- Note, this item is still in definition and probably will change.

        ::= { cpqHoClientEntry 3 }

    cpqHoClientIpAddress OBJECT-TYPE
        SYNTAX  IpAddress
        ACCESS  read-only
        STATUS  mandatory
        DESCRIPTION
            "The IP address for this client, all octets should be set to
             0xff if this machine does not support IP.  The order will be
             in network byte order (ie MSB first.)"

        ::= { cpqHoClientEntry 4 }

    cpqHoClientCommunity OBJECT-TYPE
        SYNTAX  DisplayString (SIZE (0..48))
        ACCESS  read-only
        STATUS  mandatory
        DESCRIPTION
            "A community name that can be used to query the client with SNMP.
             This community name should have, but is not required to have,
             the greatest possible access to client information."
        ::= { cpqHoClientEntry 5 }

    cpqHoClientID OBJECT-TYPE
        SYNTAX  OCTET STRING (SIZE (16))
        ACCESS  read-only
        STATUS  mandatory
        DESCRIPTION
            "The unique identifier of this client."
        ::= { cpqHoClientEntry 6 }




























































































































































































































END
