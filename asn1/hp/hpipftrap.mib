-- ****************************************************************************
--
--                  Integrity Server Trap SNMP MIB
--         Management Information Base for SNMP Network Management
--
--
--      Copyright 1993,2003-2004 Hewlett-Packard Development Company, L.P.
--
--      Hewlett-Packard Company shall not be liable for technical or
--      editorial errors or omissions contained herein. The information in
--      this document is provided "as is" without warranty of any kind and
--      is subject to change without notice. The warranties for HP products
--      are set forth in the express limited warranty statements
--      accompanying such products. Nothing herein should be construed as
--      constituting an additional warranty.
--
--      Confidential computer software. Valid license from HP required for
--      possession, use or copying. Consistent with FAR 12.211 and 12.212,
--      Commercial Computer Software, Computer Software Documentation, and
--      Technical Data for Commercial Items are licensed to the U.S.
--      Government under vendor's standard commercial license.
--
--      The Hewlett-Packard Enterprise number is 11.
--      The ASN.1 prefix to, and including the Hewlett-Packard Enterprise is:
--           1.3.6.1.4.1.11
--
-- ****************************************************************************
--
--
-- * $Date: 2006/09/28 21:48:45 $
-- * $Revision: 1.5 $
--
--   IPF Trap MIB Revision
--  =========================
--
--      MIB Rev of 1.0 is for ORCA time frame
--              - This is the initial release of this MIB.
--      2.0 - Event Data Now taken from new E0 data base
--      2.1 - Add new Hondo events
--      2.2 - Add new events for support of Eiger, Oly
--      2.3 - Add new events for PFM, other new E0 events, and new 02 events
--      2.4 - Add new events for E0 events, and 3 new temperature 02 events
--      2.5 - Add new events for E0 events Rusa , ARc
--      2.6 - Add new events for E0 events COD, HPVM
--      2.7 - Add new events for E0 events RuSa-E, Merlion
--
-- ****************************************************************************

HPIPFTRAP-MIB DEFINITIONS ::= BEGIN

IMPORTS
enterprises    FROM RFC1155-SMI
DisplayString  FROM RFC1213-MIB
OBJECT-TYPE    FROM RFC-1212
TRAP-TYPE      FROM RFC-1215;

hp                          OBJECT IDENTIFIER ::= { enterprises 11 }
nm                          OBJECT IDENTIFIER ::= { hp 2 }
hpnsa                       OBJECT IDENTIFIER ::= { nm 23 }
hpIpfE0Events               OBJECT IDENTIFIER ::= { hpnsa 35 }
hpIpf02Events               OBJECT IDENTIFIER ::= { hpnsa 45 }

-- The following are objects defined for HP IPF Event Traps

hpIpfEvtDetailStr OBJECT-TYPE
    SYNTAX DisplayString
    ACCESS read-only
    STATUS mandatory
    DESCRIPTION
      "This string provides a detailed description of the Event along with variable information."
    ::= { hpIpfE0Events 1 }


-- Traps

hpevtBadOsInitChecksum TRAP-TYPE
     ENTERPRISE hpIpfE0Events
     VARIABLES { hpIpfEvtDetailStr }
     DESCRIPTION
        "The OS has registered an OS_INIT vector, but is has not passed the checksum"

     --#SUMMARY "Invalid OS INIT checksum"
     --#ARGUMENTS {}
     --#SEVERITY WARNING
     --#TIMEINDEX 100
     --#STATE OPERATIONAL
::= 5001


hpevtBadOsMcaChecksum TRAP-TYPE
     ENTERPRISE hpIpfE0Events
     VARIABLES { hpIpfEvtDetailStr }
     DESCRIPTION
        "The OS has registered an OS_MCA vector, but it has not passed the checksum"

     --#SUMMARY "Bad OS MCA checksum"
     --#ARGUMENTS {}
     --#SEVERITY WARNING
     --#TIMEINDEX 100
     --#STATE OPERATIONAL
::= 5002


hpevtBootBmcFailed TRAP-TYPE
     ENTERPRISE hpIpfE0Events
     VARIABLES { hpIpfEvtDetailStr }
     DESCRIPTION
        "The BMC has failed testing and has been disabled."

     --#SUMMARY "BMC interface to IPMI failed"
     --#ARGUMENTS {}
     --#SEVERITY WARNING
     --#TIMEINDEX 100
     --#STATE OPERATIONAL
::= 5003


hpevtBootCellLaunchEfiFailure TRAP-TYPE
     ENTERPRISE hpIpfE0Events
     VARIABLES { hpIpfEvtDetailStr }
     DESCRIPTION
        "SFW failed to launch EFI"

     --#SUMMARY "Boot cell launch EFI failure"
     --#ARGUMENTS {}
     --#SEVERITY CRITICAL
     --#TIMEINDEX 100
     --#STATE OPERATIONAL
::= 5010


hpevtBootCellMonSelFailure TRAP-TYPE
     ENTERPRISE hpIpfE0Events
     VARIABLES { hpIpfEvtDetailStr }
     DESCRIPTION
        "Monarch selection has failed.
Data:  0x11 = Calibration Failure  0x22 = Select Code Failure"

     --#SUMMARY "Monarch selection failure"
     --#ARGUMENTS {}
     --#SEVERITY CRITICAL
     --#TIMEINDEX 100
     --#STATE OPERATIONAL
::= 5011


hpevtBootCellMonarchCollision TRAP-TYPE
     ENTERPRISE hpIpfE0Events
     VARIABLES { hpIpfEvtDetailStr }
     DESCRIPTION
        "Monarch Collision has occurred"

     --#SUMMARY "CPU monarch collision"
     --#ARGUMENTS {}
     --#SEVERITY WARNING
     --#TIMEINDEX 100
     --#STATE OPERATIONAL
::= 5013


hpevtBootCellVirtualizeEfiFailure TRAP-TYPE
     ENTERPRISE hpIpfE0Events
     VARIABLES { hpIpfEvtDetailStr }
     DESCRIPTION
        "SFW attempted to virtualize EFI and failed"

     --#SUMMARY "Boot cell virtualize EFI failure"
     --#ARGUMENTS {}
     --#SEVERITY CRITICAL
     --#TIMEINDEX 100
     --#STATE OPERATIONAL
::= 5023


hpevtBootCellVirtualizePalFailure TRAP-TYPE
     ENTERPRISE hpIpfE0Events
     VARIABLES { hpIpfEvtDetailStr }
     DESCRIPTION
        "SFW was unable to virtualize PAL"

     --#SUMMARY "Boot cell virtualize PAL failure"
     --#ARGUMENTS {}
     --#SEVERITY CRITICAL
     --#TIMEINDEX 100
     --#STATE OPERATIONAL
::= 5025


hpevtBootCellVirtualizeSalFailure TRAP-TYPE
     ENTERPRISE hpIpfE0Events
     VARIABLES { hpIpfEvtDetailStr }
     DESCRIPTION
        "SFW was unable to virtualize SAL"

     --#SUMMARY "Boot cell virtualize SAL failure"
     --#ARGUMENTS {}
     --#SEVERITY CRITICAL
     --#TIMEINDEX 100
     --#STATE OPERATIONAL
::= 5027


hpevtBootCellVirtualizeSalprocFailure TRAP-TYPE
     ENTERPRISE hpIpfE0Events
     VARIABLES { hpIpfEvtDetailStr }
     DESCRIPTION
        "SFW was unable to virtualize SALPROC"

     --#SUMMARY "Boot cell virtualize SALPROC failure"
     --#ARGUMENTS {}
     --#SEVERITY CRITICAL
     --#TIMEINDEX 100
     --#STATE OPERATIONAL
::= 5028


hpevtBootCpuConfigFail TRAP-TYPE
     ENTERPRISE hpIpfE0Events
     VARIABLES { hpIpfEvtDetailStr }
     DESCRIPTION
        "SFW has failed initializing the CPU Struct.
Data: Physical location of CPU that produced failure"

     --#SUMMARY "CPU struct init failed"
     --#ARGUMENTS {}
     --#SEVERITY WARNING
     --#TIMEINDEX 100
     --#STATE OPERATIONAL
::= 5030


hpevtBootCpuEarlyConfigFail TRAP-TYPE
     ENTERPRISE hpIpfE0Events
     VARIABLES { hpIpfEvtDetailStr }
     DESCRIPTION
        "A CPU has failed early config."

     --#SUMMARY "CPU failed early config"
     --#ARGUMENTS {}
     --#SEVERITY WARNING
     --#TIMEINDEX 100
     --#STATE OPERATIONAL
::= 5031


hpevtBootCpuEarlyTestFail TRAP-TYPE
     ENTERPRISE hpIpfE0Events
     VARIABLES { hpIpfEvtDetailStr }
     DESCRIPTION
        "A CPU has failed early self test. 
Data: PAL Test State."

     --#SUMMARY "CPU failed early selftest"
     --#ARGUMENTS {}
     --#SEVERITY WARNING
     --#TIMEINDEX 100
     --#STATE OPERATIONAL
::= 5033


hpevtBootCpuFailed TRAP-TYPE
     ENTERPRISE hpIpfE0Events
     VARIABLES { hpIpfEvtDetailStr }
     DESCRIPTION
        "SFW has detected that a CPU has failed. 
Data: The Physical Location of the CPU that failed"

     --#SUMMARY "CPU failed"
     --#ARGUMENTS {}
     --#SEVERITY WARNING
     --#TIMEINDEX 100
     --#STATE OPERATIONAL
::= 5034


hpevtBootCpuLateTestFail TRAP-TYPE
     ENTERPRISE hpIpfE0Events
     VARIABLES { hpIpfEvtDetailStr }
     DESCRIPTION
        "SFW has determined a CPU or Memory has failed late test. 
This could be related to a CPU error or a Correctable Single Bit Memory error.  
Data: Physical location of CPU
See Cause/Action."

     --#SUMMARY "CPU failed late selftest"
     --#ARGUMENTS {}
     --#SEVERITY WARNING
     --#TIMEINDEX 100
     --#STATE OPERATIONAL
::= 5036


hpevtBootCpuLateTestInsufficientMem TRAP-TYPE
     ENTERPRISE hpIpfE0Events
     VARIABLES { hpIpfEvtDetailStr }
     DESCRIPTION
        "The CPU late test has failed because of insufficient memory"

     --#SUMMARY "CPU not enough late test memory"
     --#ARGUMENTS {}
     --#SEVERITY WARNING
     --#TIMEINDEX 100
     --#STATE OPERATIONAL
::= 5037


hpevtBootEfiAllocateError TRAP-TYPE
     ENTERPRISE hpIpfE0Events
     VARIABLES { hpIpfEvtDetailStr }
     DESCRIPTION
        "Could not allocate memory for EFI image"

     --#SUMMARY "Could not allocate memory for EFI image"
     --#ARGUMENTS {}
     --#SEVERITY CRITICAL
     --#TIMEINDEX 100
     --#STATE OPERATIONAL
::= 5040


hpevtBootEfiImageCorrupt TRAP-TYPE
     ENTERPRISE hpIpfE0Events
     VARIABLES { hpIpfEvtDetailStr }
     DESCRIPTION
        "EFI image is corrupted"

     --#SUMMARY "EFI image corrupted"
     --#ARGUMENTS {}
     --#SEVERITY CRITICAL
     --#TIMEINDEX 100
     --#STATE OPERATIONAL
::= 5041


hpevtBootEfiNotInFit TRAP-TYPE
     ENTERPRISE hpIpfE0Events
     VARIABLES { hpIpfEvtDetailStr }
     DESCRIPTION
        "EFI fit error "

     --#SUMMARY "EFI not in fit table"
     --#ARGUMENTS {}
     --#SEVERITY CRITICAL
     --#TIMEINDEX 100
     --#STATE OPERATIONAL
::= 5042


hpevtBootEfiNvmFail TRAP-TYPE
     ENTERPRISE hpIpfE0Events
     VARIABLES { hpIpfEvtDetailStr }
     DESCRIPTION
        "EFI NVM has failed testing.  The cell or system will now halt."

     --#SUMMARY "NVRAM test fail"
     --#ARGUMENTS {}
     --#SEVERITY CRITICAL
     --#TIMEINDEX 100
     --#STATE OPERATIONAL
::= 5045


hpevtBootEfiRomBadSize TRAP-TYPE
     ENTERPRISE hpIpfE0Events
     VARIABLES { hpIpfEvtDetailStr }
     DESCRIPTION
        "EFI Image Error"

     --#SUMMARY "EFI Rom size bad"
     --#ARGUMENTS {}
     --#SEVERITY CRITICAL
     --#TIMEINDEX 100
     --#STATE OPERATIONAL
::= 5048


hpevtBootEfiRomXsumError TRAP-TYPE
     ENTERPRISE hpIpfE0Events
     VARIABLES { hpIpfEvtDetailStr }
     DESCRIPTION
        "EFI Image Error."

     --#SUMMARY "EFI Rom checksum error"
     --#ARGUMENTS {}
     --#SEVERITY CRITICAL
     --#TIMEINDEX 100
     --#STATE OPERATIONAL
::= 5049


hpevtBootExtIntNestLimitedExceeded TRAP-TYPE
     ENTERPRISE hpIpfE0Events
     VARIABLES { hpIpfEvtDetailStr }
     DESCRIPTION
        "The IVT interrupting nesting depth has been exceeded.  This processor will be halted.
Data: Number of the offending vector."

     --#SUMMARY "External interruption nest limit exceeded"
     --#ARGUMENTS {}
     --#SEVERITY CRITICAL
     --#TIMEINDEX 100
     --#STATE OPERATIONAL
::= 5050


hpevtBootExtIntNotServiced TRAP-TYPE
     ENTERPRISE hpIpfE0Events
     VARIABLES { hpIpfEvtDetailStr }
     DESCRIPTION
        "An external interrupt has been requested and not serviced.
Data: Number of the vector"

     --#SUMMARY "External interrupt not serviced"
     --#ARGUMENTS {}
     --#SEVERITY CRITICAL
     --#TIMEINDEX 100
     --#STATE OPERATIONAL
::= 5051


hpevtBootExtIntTaken TRAP-TYPE
     ENTERPRISE hpIpfE0Events
     VARIABLES { hpIpfEvtDetailStr }
     DESCRIPTION
        "An external interrupt has been taken. 
Data: Number of the vector taken."

     --#SUMMARY "Ext int taken"
     --#ARGUMENTS {}
     --#SEVERITY CRITICAL
     --#TIMEINDEX 100
     --#STATE OPERATIONAL
::= 5052


hpevtBootFplFailed TRAP-TYPE
     ENTERPRISE hpIpfE0Events
     VARIABLES { hpIpfEvtDetailStr }
     DESCRIPTION
        "Access to the FPL has failed."

     --#SUMMARY "Forward Progress Log (FPL) access failed"
     --#ARGUMENTS {}
     --#SEVERITY WARNING
     --#TIMEINDEX 100
     --#STATE OPERATIONAL
::= 5053


hpevtBootGetPsrFailure TRAP-TYPE
     ENTERPRISE hpIpfE0Events
     VARIABLES { hpIpfEvtDetailStr }
     DESCRIPTION
        "SFW was unable to read the CPU PSR.
Data: Physical location of CPU"

     --#SUMMARY "PSR fetch failure"
     --#ARGUMENTS {}
     --#SEVERITY CRITICAL
     --#TIMEINDEX 100
     --#STATE OPERATIONAL
::= 5054


hpevtBootHaltCell TRAP-TYPE
     ENTERPRISE hpIpfE0Events
     VARIABLES { hpIpfEvtDetailStr }
     DESCRIPTION
        "SFW has halted the cell or system"

     --#SUMMARY "Cell halt"
     --#ARGUMENTS {}
     --#SEVERITY CRITICAL
     --#TIMEINDEX 100
     --#STATE OPERATIONAL
::= 5055


hpevtBootIncompatiblePal TRAP-TYPE
     ENTERPRISE hpIpfE0Events
     VARIABLES { hpIpfEvtDetailStr }
     DESCRIPTION
        "SFW has determined that PAL is not compatible with the current processors."

     --#SUMMARY "CPU PAL incompatible with cpu"
     --#ARGUMENTS {}
     --#SEVERITY WARNING
     --#TIMEINDEX 100
     --#STATE OPERATIONAL
::= 5056


hpevtBootIncompatibleSlave TRAP-TYPE
     ENTERPRISE hpIpfE0Events
     VARIABLES { hpIpfEvtDetailStr }
     DESCRIPTION
        "SFW has determined that a slave processor is incompatible with the monarch. 
Data: Physical location of the incompatible processor."

     --#SUMMARY "Slave is incompatible with monarch"
     --#ARGUMENTS {}
     --#SEVERITY WARNING
     --#TIMEINDEX 100
     --#STATE OPERATIONAL
::= 5057


hpevtBootIntrptClearFailure TRAP-TYPE
     ENTERPRISE hpIpfE0Events
     VARIABLES { hpIpfEvtDetailStr }
     DESCRIPTION
        "Interrupt clear failed during cell config"

     --#SUMMARY "Interrupt clear failure"
     --#ARGUMENTS {}
     --#SEVERITY WARNING
     --#TIMEINDEX 100
     --#STATE OPERATIONAL
::= 5058


hpevtBootIpmiEventFailed TRAP-TYPE
     ENTERPRISE hpIpfE0Events
     VARIABLES { hpIpfEvtDetailStr }
     DESCRIPTION
        "SFW has determined that an IPMI event failed."

     --#SUMMARY "System Event Log (SEL) access failed"
     --#ARGUMENTS {}
     --#SEVERITY WARNING
     --#TIMEINDEX 100
     --#STATE OPERATIONAL
::= 5059


hpevtBootIvtOffset TRAP-TYPE
     ENTERPRISE hpIpfE0Events
     VARIABLES { hpIpfEvtDetailStr }
     DESCRIPTION
        "Data: interrupt vector table (IVT) Offset"

     --#SUMMARY "Trap taken"
     --#ARGUMENTS {}
     --#SEVERITY CRITICAL
     --#TIMEINDEX 100
     --#STATE OPERATIONAL
::= 5060


hpevtBootLdbStateBad TRAP-TYPE
     ENTERPRISE hpIpfE0Events
     VARIABLES { hpIpfEvtDetailStr }
     DESCRIPTION
        "LDB state bad   "

     --#SUMMARY "LDB State bad on entry"
     --#ARGUMENTS {}
     --#SEVERITY WARNING
     --#TIMEINDEX 100
     --#STATE OPERATIONAL
::= 5063


hpevtBootLostContextInt TRAP-TYPE
     ENTERPRISE hpIpfE0Events
     VARIABLES { hpIpfEvtDetailStr }
     DESCRIPTION
        "Interrupt context was lost.
Data: interrupt number."

     --#SUMMARY "Interrupt with ic bit clear"
     --#ARGUMENTS {}
     --#SEVERITY CRITICAL
     --#TIMEINDEX 100
     --#STATE OPERATIONAL
::= 5064


hpevtBootMinStateRegError TRAP-TYPE
     ENTERPRISE hpIpfE0Events
     VARIABLES { hpIpfEvtDetailStr }
     DESCRIPTION
        "Registering of the processor min state save area with PAL has failed."

     --#SUMMARY "Min-state registration failure"
     --#ARGUMENTS {}
     --#SEVERITY CRITICAL
     --#TIMEINDEX 100
     --#STATE OPERATIONAL
::= 5065


hpevtBootMonarchTimeout TRAP-TYPE
     ENTERPRISE hpIpfE0Events
     VARIABLES { hpIpfEvtDetailStr }
     DESCRIPTION
        "SFW has determined the monarch has timed out.  SFW is deconfiguring the CPU. 
Data: Physical Location of CPU"

     --#SUMMARY "Boot monarch timed out"
     --#ARGUMENTS {}
     --#SEVERITY WARNING
     --#TIMEINDEX 100
     --#STATE OPERATIONAL
::= 5067


hpevtBootNoPalBInFit TRAP-TYPE
     ENTERPRISE hpIpfE0Events
     VARIABLES { hpIpfEvtDetailStr }
     DESCRIPTION
        "A PAL_B FIT error has occurred"

     --#SUMMARY "PAL_B not in FIT table"
     --#ARGUMENTS {}
     --#SEVERITY CRITICAL
     --#TIMEINDEX 100
     --#STATE OPERATIONAL
::= 5069


hpevtBootNoSalBInFit TRAP-TYPE
     ENTERPRISE hpIpfE0Events
     VARIABLES { hpIpfEvtDetailStr }
     DESCRIPTION
        "A SAL_B FIT error has occurred"

     --#SUMMARY "SAL_B not in FIT table"
     --#ARGUMENTS {}
     --#SEVERITY CRITICAL
     --#TIMEINDEX 100
     --#STATE OPERATIONAL
::= 5070


hpevtBootNvmFail TRAP-TYPE
     ENTERPRISE hpIpfE0Events
     VARIABLES { hpIpfEvtDetailStr }
     DESCRIPTION
        "NVM has failed test.  The system will halt"

     --#SUMMARY "NVRAM test fail"
     --#ARGUMENTS {}
     --#SEVERITY CRITICAL
     --#TIMEINDEX 100
     --#STATE OPERATIONAL
::= 5073


hpevtBootOutOfRangeVector TRAP-TYPE
     ENTERPRISE hpIpfE0Events
     VARIABLES { hpIpfEvtDetailStr }
     DESCRIPTION
        "A interrupt vector has been requested out of the acceptible range.
Data: Vector Number."

     --#SUMMARY "Interrupt vector out of range"
     --#ARGUMENTS {}
     --#SEVERITY CRITICAL
     --#TIMEINDEX 100
     --#STATE OPERATIONAL
::= 5076


hpevtBootPalCopyInfoError TRAP-TYPE
     ENTERPRISE hpIpfE0Events
     VARIABLES { hpIpfEvtDetailStr }
     DESCRIPTION
        "The PAL Copy Info call has failed."

     --#SUMMARY "Pal proc error getting pal copy info"
     --#ARGUMENTS {}
     --#SEVERITY CRITICAL
     --#TIMEINDEX 100
     --#STATE OPERATIONAL
::= 5077


hpevtBootPalCopyPalError TRAP-TYPE
     ENTERPRISE hpIpfE0Events
     VARIABLES { hpIpfEvtDetailStr }
     DESCRIPTION
        "Error copying PAL to memory"

     --#SUMMARY "Pal proc error copying pal to memory"
     --#ARGUMENTS {}
     --#SEVERITY CRITICAL
     --#TIMEINDEX 100
     --#STATE OPERATIONAL
::= 5078


hpevtBootPalProcFailure TRAP-TYPE
     ENTERPRISE hpIpfE0Events
     VARIABLES { hpIpfEvtDetailStr }
     DESCRIPTION
        "A PAL Proc has failed.  This will halt the processor. 
Data: Physical Location of CPU"

     --#SUMMARY "Boot pal proc failure"
     --#ARGUMENTS {}
     --#SEVERITY WARNING
     --#TIMEINDEX 100
     --#STATE OPERATIONAL
::= 5079


hpevtBootPlatConsoleDevFailed TRAP-TYPE
     ENTERPRISE hpIpfE0Events
     VARIABLES { hpIpfEvtDetailStr }
     DESCRIPTION
        "A console device has failed. 
Data: Physical Addr of device that failed."

     --#SUMMARY "Console device failure"
     --#ARGUMENTS {}
     --#SEVERITY WARNING
     --#TIMEINDEX 100
     --#STATE OPERATIONAL
::= 5080


hpevtBootPlatIntfcDevFailed TRAP-TYPE
     ENTERPRISE hpIpfE0Events
     VARIABLES { hpIpfEvtDetailStr }
     DESCRIPTION
        "A console device has failed.
Data: Physical Addr of device that failed."

     --#SUMMARY "Platform interface device failure"
     --#ARGUMENTS {}
     --#SEVERITY WARNING
     --#TIMEINDEX 100
     --#STATE OPERATIONAL
::= 5081


hpevtBootPlatScrBad TRAP-TYPE
     ENTERPRISE hpIpfE0Events
     VARIABLES { hpIpfEvtDetailStr }
     DESCRIPTION
        "Platform Scratch RAM has failed the test."

     --#SUMMARY "platform scratch RAM test failed"
     --#ARGUMENTS {}
     --#SEVERITY WARNING
     --#TIMEINDEX 100
     --#STATE OPERATIONAL
::= 5082


hpevtBootRendezFailure TRAP-TYPE
     ENTERPRISE hpIpfE0Events
     VARIABLES { hpIpfEvtDetailStr }
     DESCRIPTION
        "A CPU has failed to enter rendezvous. 
Data: Local CPU Number"

     --#SUMMARY "CPU rendezvous failure"
     --#ARGUMENTS {}
     --#SEVERITY WARNING
     --#TIMEINDEX 100
     --#STATE OPERATIONAL
::= 5083


hpevtBootSalExtractError TRAP-TYPE
     ENTERPRISE hpIpfE0Events
     VARIABLES { hpIpfEvtDetailStr }
     DESCRIPTION
        "SFW could not extract SAL_B from the ROM"

     --#SUMMARY "Error extracting sal_b from rom"
     --#ARGUMENTS {}
     --#SEVERITY CRITICAL
     --#TIMEINDEX 100
     --#STATE OPERATIONAL
::= 5084


hpevtBootScrFail TRAP-TYPE
     ENTERPRISE hpIpfE0Events
     VARIABLES { hpIpfEvtDetailStr }
     DESCRIPTION
        "Platform Scratch RAM has failed test."

     --#SUMMARY "Scratch RAM bad"
     --#ARGUMENTS {}
     --#SEVERITY CRITICAL
     --#TIMEINDEX 100
     --#STATE OPERATIONAL
::= 5085


hpevtBootSelFull TRAP-TYPE
     ENTERPRISE hpIpfE0Events
     VARIABLES { hpIpfEvtDetailStr }
     DESCRIPTION
        "IPMI SEL full   "

     --#SUMMARY "IPMI System Event Log (SEL) is full"
     --#ARGUMENTS {}
     --#SEVERITY WARNING
     --#TIMEINDEX 100
     --#STATE OPERATIONAL
::= 5087


hpevtBootSlaveNoFinalWakeupVector TRAP-TYPE
     ENTERPRISE hpIpfE0Events
     VARIABLES { hpIpfEvtDetailStr }
     DESCRIPTION
        "No wakeup vector registered for processor 
Data: Physical location of CPU"

     --#SUMMARY "Slave wakeup before vector registered"
     --#ARGUMENTS {}
     --#SEVERITY WARNING
     --#TIMEINDEX 100
     --#STATE OPERATIONAL
::= 5091


hpevtBootSlaveRendezHandlerFail TRAP-TYPE
     ENTERPRISE hpIpfE0Events
     VARIABLES { hpIpfEvtDetailStr }
     DESCRIPTION
        "Slave Rendezvous handler has failed. 
Data: Physical Location of CPU"

     --#SUMMARY "CPU failed rendezvous handler"
     --#ARGUMENTS {}
     --#SEVERITY WARNING
     --#TIMEINDEX 100
     --#STATE OPERATIONAL
::= 5092


hpevtBootSmbiosBuildError TRAP-TYPE
     ENTERPRISE hpIpfE0Events
     VARIABLES { hpIpfEvtDetailStr }
     DESCRIPTION
        "SFW failed to build the SMBIOS tables"

     --#SUMMARY "Error building SMBIOS Tables"
     --#ARGUMENTS {}
     --#SEVERITY CRITICAL
     --#TIMEINDEX 100
     --#STATE OPERATIONAL
::= 5098


hpevtBootTrapNestLimitedExceeded TRAP-TYPE
     ENTERPRISE hpIpfE0Events
     VARIABLES { hpIpfEvtDetailStr }
     DESCRIPTION
        "The trap nesting limit has been exceeded. 
Data: Vector Number"

     --#SUMMARY "Trap nest limit exceeded"
     --#ARGUMENTS {}
     --#SEVERITY CRITICAL
     --#TIMEINDEX 100
     --#STATE OPERATIONAL
::= 5100


hpevtBootTrapNotServiced TRAP-TYPE
     ENTERPRISE hpIpfE0Events
     VARIABLES { hpIpfEvtDetailStr }
     DESCRIPTION
        "A trap has been requested and not serviced. 
Data: Vector Number"

     --#SUMMARY "Trap not serviced"
     --#ARGUMENTS {}
     --#SEVERITY CRITICAL
     --#TIMEINDEX 100
     --#STATE OPERATIONAL
::= 5101


hpevtBootTrapTaken TRAP-TYPE
     ENTERPRISE hpIpfE0Events
     VARIABLES { hpIpfEvtDetailStr }
     DESCRIPTION
        "A trap  has been taken. 
Data: Number of the vector taken."

     --#SUMMARY "Trap taken"
     --#ARGUMENTS {}
     --#SEVERITY CRITICAL
     --#TIMEINDEX 100
     --#STATE OPERATIONAL
::= 5102


hpevtBootUnclearedInt TRAP-TYPE
     ENTERPRISE hpIpfE0Events
     VARIABLES { hpIpfEvtDetailStr }
     DESCRIPTION
        "At least one interrupt was not cleared. 
Data: The highest pending interrupt number"

     --#SUMMARY "Uncleared interrupt"
     --#ARGUMENTS {}
     --#SEVERITY WARNING
     --#TIMEINDEX 100
     --#STATE OPERATIONAL
::= 5103


hpevtBootUnexpectedExtIntPostRedirTable TRAP-TYPE
     ENTERPRISE hpIpfE0Events
     VARIABLES { hpIpfEvtDetailStr }
     DESCRIPTION
        "An unexpected external interrupt has occurred. 
Data: External Interrupt Number"

     --#SUMMARY "Unexpected external interrupt"
     --#ARGUMENTS {}
     --#SEVERITY CRITICAL
     --#TIMEINDEX 100
     --#STATE OPERATIONAL
::= 5104


hpevtBootUnexpectedIntPreRedirTable TRAP-TYPE
     ENTERPRISE hpIpfE0Events
     VARIABLES { hpIpfEvtDetailStr }
     DESCRIPTION
        "An interrupt has occurred before setting up the Interrupt Vector Table.
Data: Interrupt Number"

     --#SUMMARY "Interrupt before redirection table set up"
     --#ARGUMENTS {}
     --#SEVERITY CRITICAL
     --#TIMEINDEX 100
     --#STATE OPERATIONAL
::= 5105


hpevtBootUnexpectedMca TRAP-TYPE
     ENTERPRISE hpIpfE0Events
     VARIABLES { hpIpfEvtDetailStr }
     DESCRIPTION
        "An unexpected MCA has occurred before MCA's are unmasked. 
Data: Local CPU Number."

     --#SUMMARY "CPU unexpected MCA"
     --#ARGUMENTS {}
     --#SEVERITY CRITICAL
     --#TIMEINDEX 100
     --#STATE OPERATIONAL
::= 5106


hpevtBootUnexpectedTrapPostRedirTable TRAP-TYPE
     ENTERPRISE hpIpfE0Events
     VARIABLES { hpIpfEvtDetailStr }
     DESCRIPTION
        "An unexpected trap has occurred.  The trap number is either invalid or the requested trap has not been registered.
Data: Trap Number"

     --#SUMMARY "Unexpected trap"
     --#ARGUMENTS {}
     --#SEVERITY CRITICAL
     --#TIMEINDEX 100
     --#STATE OPERATIONAL
::= 5107


hpevtBootUnknownFailure TRAP-TYPE
     ENTERPRISE hpIpfE0Events
     VARIABLES { hpIpfEvtDetailStr }
     DESCRIPTION
        "SFW has detected an unknown error."

     --#SUMMARY "CPU unknown boot error"
     --#ARGUMENTS {}
     --#SEVERITY CRITICAL
     --#TIMEINDEX 100
     --#STATE OPERATIONAL
::= 5108


hpevtErrorsPalFailure TRAP-TYPE
     ENTERPRISE hpIpfE0Events
     VARIABLES { hpIpfEvtDetailStr }
     DESCRIPTION
        "SFW has detected a PAL Failure"

     --#SUMMARY "CC errors PAL failure"
     --#ARGUMENTS {}
     --#SEVERITY WARNING
     --#TIMEINDEX 100
     --#STATE OPERATIONAL
::= 5118


hpevtExpMcNotRegistered TRAP-TYPE
     ENTERPRISE hpIpfE0Events
     VARIABLES { hpIpfEvtDetailStr }
     DESCRIPTION
        "Expected Machine Check Vector not registered"

     --#SUMMARY "Expected MC vector unregistered"
     --#ARGUMENTS {}
     --#SEVERITY WARNING
     --#TIMEINDEX 100
     --#STATE OPERATIONAL
::= 5119


hpevtInitInitiated TRAP-TYPE
     ENTERPRISE hpIpfE0Events
     VARIABLES { hpIpfEvtDetailStr }
     DESCRIPTION
        "This is the equivalent of a TOC event in the PA RISC Architecture.  On IPF systems, this event is called an INIT. 
This event can be triggered by the 'tc' command from the MP, or from the button labeled 'TOC' :wor 'Transfer of Control' on the Management card or bezel of the system.  There are also other causes of an INIT generated by software. 
Data: Local CPU Number"

     --#SUMMARY "INIT initiated"
     --#ARGUMENTS {}
     --#SEVERITY CRITICAL
     --#TIMEINDEX 100
     --#STATE OPERATIONAL
::= 5121


hpevtIoCheckLbaMissingErr TRAP-TYPE
     ENTERPRISE hpIpfE0Events
     VARIABLES { hpIpfEvtDetailStr }
     DESCRIPTION
        "An I/O host bridge is missing.  Firmware will continue boot and display the following EFI warning, 'Unexpected hardware I/O configuration.' 
Data Field: Physical location of the missing I/O host bridge."

     --#SUMMARY "Expected I/O host bridge is missing "
     --#ARGUMENTS {}
     --#SEVERITY WARNING
     --#TIMEINDEX 100
     --#STATE OPERATIONAL
::= 5123


hpevtIoCheckNumSlotsErr TRAP-TYPE
     ENTERPRISE hpIpfE0Events
     VARIABLES { hpIpfEvtDetailStr }
     DESCRIPTION
        "Firmware detected an unexpected number of I/O slots connected to an I/O host bridge.  Firmware display the following EFI warning message, 'Unexpected hardware I/O configuration.' 
Data Field: Physical location of the I/O host bridge."

     --#SUMMARY "LBA has unexpected number of I/O slots"
     --#ARGUMENTS {}
     --#SEVERITY WARNING
     --#TIMEINDEX 100
     --#STATE OPERATIONAL
::= 5124


hpevtIoCheckRopeWidthErr TRAP-TYPE
     ENTERPRISE hpIpfE0Events
     VARIABLES { hpIpfEvtDetailStr }
     DESCRIPTION
        "Firmware found an I/O controller rope of unexpected width.  Firmware will configure the I/O host bridge connected to the rope and display the following EFI warning message, 'Unexpected hardware I/O configuration.' 
Data Field: Physical location of the I/O host bridge connected to the rope."

     --#SUMMARY "I/O rope width does not match expected value"
     --#ARGUMENTS {}
     --#SEVERITY WARNING
     --#TIMEINDEX 100
     --#STATE OPERATIONAL
::= 5125


hpevtIoCheckXtraLbaFoundErr TRAP-TYPE
     ENTERPRISE hpIpfE0Events
     VARIABLES { hpIpfEvtDetailStr }
     DESCRIPTION
        "Firmware found an unexpected I/O host bridge.  Firmware will configure the I/O host bridge and display the following EFI warning message, 'Unexpected hardware I/O configuration.' 
Data Field: Physical location of the unexpected I/O host bridge."

     --#SUMMARY "Found unexpected I/O host bridge"
     --#ARGUMENTS {}
     --#SEVERITY WARNING
     --#TIMEINDEX 100
     --#STATE OPERATIONAL
::= 5127


hpevtIoDllError TRAP-TYPE
     ENTERPRISE hpIpfE0Events
     VARIABLES { hpIpfEvtDetailStr }
     DESCRIPTION
        "An I/O host bridge's bus frequency DLL circuit failed.  Firmware will deconfigure the failed I/O host bridge and display the following EFI warning message, 'Failed I/O slot(s) deconfigured.' 
Data Field: Physical location of the I/O host bridge."

     --#SUMMARY "PCI clock DLL error"
     --#ARGUMENTS {}
     --#SEVERITY WARNING
     --#TIMEINDEX 100
     --#STATE OPERATIONAL
::= 5130


hpevtIoHotPlugCtrlFailed TRAP-TYPE
     ENTERPRISE hpIpfE0Events
     VARIABLES { hpIpfEvtDetailStr }
     DESCRIPTION
        "An I/O host bridge's hot-plug controller has failed.  Firmware will deconfigure the I/O host bridge and display the following EFI warning message, 'Failed I/O slot(s) deconfigured.' 
Data Field: Physical location of the I/O host bridge."

     --#SUMMARY "PCI hot plug controller failed"
     --#ARGUMENTS {}
     --#SEVERITY WARNING
     --#TIMEINDEX 100
     --#STATE OPERATIONAL
::= 5131


hpevtIoInvalidRopeBundle TRAP-TYPE
     ENTERPRISE hpIpfE0Events
     VARIABLES { hpIpfEvtDetailStr }
     DESCRIPTION
        "Firmware attempts to configure an I/O controller rope to an unsupported width.  Firmware will deconfigure any I/O host bridge connected to the rope. 
Data Field: Physical location of the failed rope."

     --#SUMMARY "Found unknown I/O rope width"
     --#ARGUMENTS {}
     --#SEVERITY WARNING
     --#TIMEINDEX 100
     --#STATE OPERATIONAL
::= 5132


hpevtIoLbaClearErrFailed TRAP-TYPE
     ENTERPRISE hpIpfE0Events
     VARIABLES { hpIpfEvtDetailStr }
     DESCRIPTION
        "During I/O host bridge configuration, firmware found a persistent error condition.  Firmware will deconfigure the I/O host bridge and display the following EFI warning message, 'Failed I/O slot(s) deconfigured.' 
Data Field: Physical location of the I/O host bridge."

     --#SUMMARY "I/O LBA clear error failed"
     --#ARGUMENTS {}
     --#SEVERITY WARNING
     --#TIMEINDEX 100
     --#STATE OPERATIONAL
::= 5133


hpevtIoLbaResetError TRAP-TYPE
     ENTERPRISE hpIpfE0Events
     VARIABLES { hpIpfEvtDetailStr }
     DESCRIPTION
        "An I/O host bridge is inaccessible because an I/O controller rope reset failed to complete.  Firmware will deconfigure the I/O host bridge and display the following EFI warning message, 'Failed I/O slot(s) deconfigured.' 
Data Field: Physical location of the I/O host bridge."

     --#SUMMARY "I/O host bridge inaccessible because rope reset failed to complete"
     --#ARGUMENTS {}
     --#SEVERITY WARNING
     --#TIMEINDEX 100
     --#STATE OPERATIONAL
::= 5136


hpevtIoNotEnoughPowerError TRAP-TYPE
     ENTERPRISE hpIpfE0Events
     VARIABLES { hpIpfEvtDetailStr }
     DESCRIPTION
        "There is insufficient power.  Firmware will not power on a hot-plug I/O slot.  In addition, firmware will display the following EFI warning message, 'Failed I/O slot(s) deconfigured.'
Date Field: Physical location of the I/O slot."

     --#SUMMARY "Insufficient power to turn on PCI slot"
     --#ARGUMENTS {}
     --#SEVERITY WARNING
     --#TIMEINDEX 100
     --#STATE OPERATIONAL
::= 5137


hpevtIoPciMappingFailed TRAP-TYPE
     ENTERPRISE hpIpfE0Events
     VARIABLES { hpIpfEvtDetailStr }
     DESCRIPTION
        "Firmware encountered an unexpected error while attempting to configure an I/O host bridge's I/O devices.  Firmware will continue boot but will not configure the I/O devices connected to the specified I/O host bridge.  Such I/O devices will not be usable as console nor boot devices but might be usable by the O/S. 
Data Field: Physical location of the I/O host bridge."

     --#SUMMARY "PCI bus walk unknown error"
     --#ARGUMENTS {}
     --#SEVERITY WARNING
     --#TIMEINDEX 100
     --#STATE OPERATIONAL
::= 5138


hpevtIoPciMappingTooBig TRAP-TYPE
     ENTERPRISE hpIpfE0Events
     VARIABLES { hpIpfEvtDetailStr }
     DESCRIPTION
        "The total resource requirement from the I/O devices connected to an I/O host bridge exceeds the resource limit of the I/O host bridge.  Firmware will continue boot but will not configure the I/O devices connected to the specified I/O host bridge. In addition, firmware will display the following EFI warning message, 'Insufficient resources to assign to one or more I/O devices.'   Such I/O devices will not be usable as console nor boot devices but might be usable by the O/S. 
Data Field: Physical location of the I/O host bridge."

     --#SUMMARY "PCI bus walk resources exceeded"
     --#ARGUMENTS {}
     --#SEVERITY WARNING
     --#TIMEINDEX 100
     --#STATE OPERATIONAL
::= 5139


hpevtIoPciUnmappingFailed TRAP-TYPE
     ENTERPRISE hpIpfE0Events
     VARIABLES { hpIpfEvtDetailStr }
     DESCRIPTION
        "Firmware encountered an unexpected error while attempting to clear resource allocations on an I/O host bridge's I/O devices. 
Data Field: Physical location of the I/O host bridge."

     --#SUMMARY "PCI bus unmap unknown error"
     --#ARGUMENTS {}
     --#SEVERITY WARNING
     --#TIMEINDEX 100
     --#STATE OPERATIONAL
::= 5140


hpevtIoPcixcapSampleError TRAP-TYPE
     ENTERPRISE hpIpfE0Events
     VARIABLES { hpIpfEvtDetailStr }
     DESCRIPTION
        "An I/O host bridge failed to determine the appropriate PCI[X] mode and frequency (PCI, PCI-X 66 MHz, PCI-X 133 MHz, etc.) for its bus.  Firmware will deconfigure the I/O host bridge and display the following EFI warning message, 'Failed I/O slot(s) deconfigured.' 
Data Field: Physical location of the failed I/O host bridge."

     --#SUMMARY "PCIXCAP sampling error"
     --#ARGUMENTS {}
     --#SEVERITY WARNING
     --#TIMEINDEX 100
     --#STATE OPERATIONAL
::= 5141


hpevtIoPmNotRespondingError TRAP-TYPE
     ENTERPRISE hpIpfE0Events
     VARIABLES { hpIpfEvtDetailStr }
     DESCRIPTION
        "Firmware is unable to access the power monitor.  Firmware will assume that there is sufficient power and proceed to power on an I/O slot. 
Data Field: Physical location of the I/O slot."

     --#SUMMARY "Power monitor failed to respond"
     --#ARGUMENTS {}
     --#SEVERITY WARNING
     --#TIMEINDEX 100
     --#STATE OPERATIONAL
::= 5142


hpevtIoRopeResetError TRAP-TYPE
     ENTERPRISE hpIpfE0Events
     VARIABLES { hpIpfEvtDetailStr }
     DESCRIPTION
        "An I/O controller rope reset did not complete within the expected time limit.  Firmware will deconfigure the I/O host bridge attached to the rope. 
Data Field: Physical location of the deconfigured I/O host bridge."

     --#SUMMARY "I/O rope reset failed to complete"
     --#ARGUMENTS {}
     --#SEVERITY WARNING
     --#TIMEINDEX 100
     --#STATE OPERATIONAL
::= 5143


hpevtIoSbaClearErrFailed TRAP-TYPE
     ENTERPRISE hpIpfE0Events
     VARIABLES { hpIpfEvtDetailStr }
     DESCRIPTION
        "During I/O chipset configuration, firmware found a persistent error condition.  Firmware will attempt to continue the boot. 
Data Field: Physical location of the I/O chipset."

     --#SUMMARY "I/O SBA clear error failed"
     --#ARGUMENTS {}
     --#SEVERITY WARNING
     --#TIMEINDEX 100
     --#STATE OPERATIONAL
::= 5144


hpevtIoSlotPowerDefaultError TRAP-TYPE
     ENTERPRISE hpIpfE0Events
     VARIABLES { hpIpfEvtDetailStr }
     DESCRIPTION
        "During boot, firmware has found a hot-plug I/O slot with an incorrect default power state.  The slot power should be off by default. 
Data Field: Physical location of the I/O slot."

     --#SUMMARY "PCI slot has incorrect default power state"
     --#ARGUMENTS {}
     --#SEVERITY WARNING
     --#TIMEINDEX 100
     --#STATE OPERATIONAL
::= 5145


hpevtIoSlotPowerOnError TRAP-TYPE
     ENTERPRISE hpIpfE0Events
     VARIABLES { hpIpfEvtDetailStr }
     DESCRIPTION
        "Firmware encountered an error while attempting to power on an I/O slot.  Firmware will deconfigure the I/O slot and display the following EFI warning message, 'Failed I/O slot(s) deconfigured.' 
Data Field: Physical location of the I/O slot."

     --#SUMMARY "PCI slot power on error"
     --#ARGUMENTS {}
     --#SEVERITY WARNING
     --#TIMEINDEX 100
     --#STATE OPERATIONAL
::= 5146


hpevtIoSlotStandbyPowerError TRAP-TYPE
     ENTERPRISE hpIpfE0Events
     VARIABLES { hpIpfEvtDetailStr }
     DESCRIPTION
        "An I/O slot's standby (Vaux) power has failed.  Firmware will deconfigure the I/O slot and display the following EFI warning message, 'Failed I/O slot(s) deconfigured.' 
Data Field: Physical location of the failed I/O slot."

     --#SUMMARY "PCI slot's standby power failed"
     --#ARGUMENTS {}
     --#SEVERITY WARNING
     --#TIMEINDEX 100
     --#STATE OPERATIONAL
::= 5147


hpevtIoUnknownPcixcapVal TRAP-TYPE
     ENTERPRISE hpIpfE0Events
     VARIABLES { hpIpfEvtDetailStr }
     DESCRIPTION
        "An I/O host bridge or hot-plug controller reported an illegal PCI[X] bus mode for its bus or slot, respectively.  Firmware will deconfigure the I/O host bridge or I/O slot and display the following EFI warning, 'Failed I/O slot(s) deconfigured.' 
Data Field: Physical location of the failed I/O host bridge or the failed I/O slot."

     --#SUMMARY "Found invalid PCIXCAP value"
     --#ARGUMENTS {}
     --#SEVERITY WARNING
     --#TIMEINDEX 100
     --#STATE OPERATIONAL
::= 5148


hpevtIoUnsupRopeFreq TRAP-TYPE
     ENTERPRISE hpIpfE0Events
     VARIABLES { hpIpfEvtDetailStr }
     DESCRIPTION
        "Firmware attempted to configure an I/O controller rope to an unsupported frequency.  Firmware will deconfigure any I/O host bridge connected to the rope and display the following EFI warning message, 'Failed I/O slot(s) deconfigured.' 
Data Field: Physical location of the failed rope."

     --#SUMMARY "Unsupported rope frequency"
     --#ARGUMENTS {}
     --#SEVERITY WARNING
     --#TIMEINDEX 100
     --#STATE OPERATIONAL
::= 5149


hpevtIoUnsupportedLba TRAP-TYPE
     ENTERPRISE hpIpfE0Events
     VARIABLES { hpIpfEvtDetailStr }
     DESCRIPTION
        "Firmware has found an unsupported I/O host bridge type.  Firmware will deconfigure the I/O host bridge and display the following EFI warning message, 'Failed I/O slot(s) deconfigured.' 
Data Field: Physical location of the I/O host bridge."

     --#SUMMARY "Unsupported host bridge type"
     --#ARGUMENTS {}
     --#SEVERITY WARNING
     --#TIMEINDEX 100
     --#STATE OPERATIONAL
::= 5150


hpevtMcInitiated TRAP-TYPE
     ENTERPRISE hpIpfE0Events
     VARIABLES { hpIpfEvtDetailStr }
     DESCRIPTION
        "A Machine Check has been initiated"

     --#SUMMARY "Machine Check initiated"
     --#ARGUMENTS {}
     --#SEVERITY CRITICAL
     --#TIMEINDEX 100
     --#STATE OPERATIONAL
::= 5152


hpevtMdtConstructAreaBad TRAP-TYPE
     ENTERPRISE hpIpfE0Events
     VARIABLES { hpIpfEvtDetailStr }
     DESCRIPTION
        "There has been a problem building the Memory Data Table (MDT)."

     --#SUMMARY "Error in temporary mdt area"
     --#ARGUMENTS {}
     --#SEVERITY CRITICAL
     --#TIMEINDEX 100
     --#STATE OPERATIONAL
::= 5155


hpevtMdtLmmioEntryNotFound TRAP-TYPE
     ENTERPRISE hpIpfE0Events
     VARIABLES { hpIpfEvtDetailStr }
     DESCRIPTION
        "There has been a problem building the Memory Data Table (MDT)."

     --#SUMMARY "Failed to find lmmio entry in mdt"
     --#ARGUMENTS {}
     --#SEVERITY CRITICAL
     --#TIMEINDEX 100
     --#STATE OPERATIONAL
::= 5156


hpevtMdtPageZeroBad TRAP-TYPE
     ENTERPRISE hpIpfE0Events
     VARIABLES { hpIpfEvtDetailStr }
     DESCRIPTION
        "Memory page 0 was slated for deallocation in the PDT.  EFI cannot launch with page 0 bad, so the system will halt."

     --#SUMMARY "Memory page zero bad"
     --#ARGUMENTS {}
     --#SEVERITY CRITICAL
     --#TIMEINDEX 100
     --#STATE OPERATIONAL
::= 5157


hpevtMdtUnableToFindSpace TRAP-TYPE
     ENTERPRISE hpIpfE0Events
     VARIABLES { hpIpfEvtDetailStr }
     DESCRIPTION
        "There has been a problem building the Memory Data Table (MDT)."

     --#SUMMARY "Failed to find space in mdt"
     --#ARGUMENTS {}
     --#SEVERITY CRITICAL
     --#TIMEINDEX 100
     --#STATE OPERATIONAL
::= 5158


hpevtMediaFailure TRAP-TYPE
     ENTERPRISE hpIpfE0Events
     VARIABLES { hpIpfEvtDetailStr }
     DESCRIPTION
        "There has been a media failure."

     --#SUMMARY "Media failure: info was not retrieved/logged"
     --#ARGUMENTS {}
     --#SEVERITY WARNING
     --#TIMEINDEX 100
     --#STATE OPERATIONAL
::= 5159


hpevtMemBibRegFailure TRAP-TYPE
     ENTERPRISE hpIpfE0Events
     VARIABLES { hpIpfEvtDetailStr }
     DESCRIPTION
        "Indicates that the chipset register test has failed.  The data field contains the physical address of the failing register."

     --#SUMMARY "Bus interface register test failed"
     --#ARGUMENTS {}
     --#SEVERITY WARNING
     --#TIMEINDEX 100
     --#STATE OPERATIONAL
::= 5160


hpevtMemCacheLine0WrRdFailed TRAP-TYPE
     ENTERPRISE hpIpfE0Events
     VARIABLES { hpIpfEvtDetailStr }
     DESCRIPTION
        "After FW's first access to main memory, FW detected that the CEC logged an error after reading back what was just written."

     --#SUMMARY "Memory ECC normal write/read test failed"
     --#ARGUMENTS {}
     --#SEVERITY WARNING
     --#TIMEINDEX 100
     --#STATE OPERATIONAL
::= 5161


hpevtMemDimmLoadOrderErr TRAP-TYPE
     ENTERPRISE hpIpfE0Events
     VARIABLES { hpIpfEvtDetailStr }
     DESCRIPTION
        "A DIMM that is required to be loaded in order for this DIMM to function properly is not loaded, so FW will deallocate this DIMM.  Currently, none of the platforms require any DIMMs to be loaded in order for this DIMM to work properly."

     --#SUMMARY "DIMM loading order error:  DIMM  deallocated"
     --#ARGUMENTS {}
     --#SEVERITY WARNING
     --#TIMEINDEX 100
     --#STATE OPERATIONAL
::= 5171


hpevtMemDimmSpdChecksum TRAP-TYPE
     ENTERPRISE hpIpfE0Events
     VARIABLES { hpIpfEvtDetailStr }
     DESCRIPTION
        "The DIMM specified by the physical location has an SPD EEPROM that has a bad checksum.  The Data field is the physical location of the DIMM."

     --#SUMMARY "DIMM SPD checksum failed"
     --#ARGUMENTS {}
     --#SEVERITY WARNING
     --#TIMEINDEX 100
     --#STATE OPERATIONAL
::= 5172


hpevtMemDimmSpdFatal TRAP-TYPE
     ENTERPRISE hpIpfE0Events
     VARIABLES { hpIpfEvtDetailStr }
     DESCRIPTION
        "Detected a error in DIMM SPD"

     --#SUMMARY "DIMM SPD fatal error"
     --#ARGUMENTS {}
     --#SEVERITY WARNING
     --#TIMEINDEX 100
     --#STATE OPERATIONAL
::= 5173


hpevtMemDimmTypeIncompatible TRAP-TYPE
     ENTERPRISE hpIpfE0Events
     VARIABLES { hpIpfEvtDetailStr }
     DESCRIPTION
        "A DIMM was installed whose DIMM type is not compatible with the current set of supported DIMMs for this platform."

     --#SUMMARY "Unsupported memory DIMM type"
     --#ARGUMENTS {}
     --#SEVERITY WARNING
     --#TIMEINDEX 100
     --#STATE OPERATIONAL
::= 5174


hpevtMemDimmTypeMismatch TRAP-TYPE
     ENTERPRISE hpIpfE0Events
     VARIABLES { hpIpfEvtDetailStr }
     DESCRIPTION
        "The DIMM type of this DIMM is not the same as the other DIMMs in the same group. The group of DIMMs is deallocated. If this is the last active group of DIMMs in the system, the system is halted."

     --#SUMMARY "The DIMM type of this DIMM doesn't match with others in the DIMM group"
     --#ARGUMENTS {}
     --#SEVERITY WARNING
     --#TIMEINDEX 100
     --#STATE OPERATIONAL
::= 5175


hpevtMemDimmTypeTableFull TRAP-TYPE
     ENTERPRISE hpIpfE0Events
     VARIABLES { hpIpfEvtDetailStr }
     DESCRIPTION
        "The DIMM type table is full"

     --#SUMMARY "The DIMM type table is full. New DIMM type cannot be added."
     --#ARGUMENTS {}
     --#SEVERITY WARNING
     --#TIMEINDEX 100
     --#STATE OPERATIONAL
::= 5176


hpevtMemDmtEntryNotFound TRAP-TYPE
     ENTERPRISE hpIpfE0Events
     VARIABLES { hpIpfEvtDetailStr }
     DESCRIPTION
        "An entry for the DIMM was not found in the DMT table.  The data field contains the DMT entry that the caller wanted to find (in Dimm number format, which is 2 bytes, upper byte is the extender number, lower byte is the chipselect of the rank caller is looking for.)"

     --#SUMMARY "DIMM number not found in DMT Table"
     --#ARGUMENTS {}
     --#SEVERITY WARNING
     --#TIMEINDEX 100
     --#STATE OPERATIONAL
::= 5179


hpevtMemEccMbeDataTstFailed TRAP-TYPE
     ENTERPRISE hpIpfE0Events
     VARIABLES { hpIpfEvtDetailStr }
     DESCRIPTION
        "The FW selftest of CEC multi-bit error (MBE) detection has failed.  The upper 32 bits of the data field contain the Dword offset within the cacheline of the failed MBE detection.  The lower 32 bits are split in two, and they contain the bit numbers within the Dword that were flipped in order to cause an MBE."

     --#SUMMARY "Memory ECC multiple-bit data error detection failed"
     --#ARGUMENTS {}
     --#SEVERITY WARNING
     --#TIMEINDEX 100
     --#STATE OPERATIONAL
::= 5180


hpevtMemEccMbeSignalTstFailed TRAP-TYPE
     ENTERPRISE hpIpfE0Events
     VARIABLES { hpIpfEvtDetailStr }
     DESCRIPTION
        "The FW selftest of CEC multi-bit error (MBE) signaling has failed.  The upper 32 bits of the data field contain the Dword offset within the cacheline of the failed MBE detection.  The lower 32 bits are split in two, and they contain the bit numbers within the Dword that were flipped in order to cause an MBE."

     --#SUMMARY "Memory ECC multiple-bit ECC error signalling failed"
     --#ARGUMENTS {}
     --#SEVERITY WARNING
     --#TIMEINDEX 100
     --#STATE OPERATIONAL
::= 5181


hpevtMemEccSbeDataTstFailed TRAP-TYPE
     ENTERPRISE hpIpfE0Events
     VARIABLES { hpIpfEvtDetailStr }
     DESCRIPTION
        "The FW selftest of CEC single-bit error (SBE) detection has failed.  The data field contains the bit within the Dword that was flipped that caused the CEC to not see an SBE."

     --#SUMMARY "Memory ECC single-bit data error detection failed"
     --#ARGUMENTS {}
     --#SEVERITY WARNING
     --#TIMEINDEX 100
     --#STATE OPERATIONAL
::= 5182


hpevtMemEccSbeEccTstFailed TRAP-TYPE
     ENTERPRISE hpIpfE0Events
     VARIABLES { hpIpfEvtDetailStr }
     DESCRIPTION
        "The FW selftest of CEC single-bit error (SBE) detection has failed.  The data field contains the bit within the Dword that was flipped that caused the CEC to not see an SBE."

     --#SUMMARY "Memory ECC single-bit ECC error detection failed"
     --#ARGUMENTS {}
     --#SEVERITY WARNING
     --#TIMEINDEX 100
     --#STATE OPERATIONAL
::= 5183


hpevtMemEnoughMemFailed TRAP-TYPE
     ENTERPRISE hpIpfE0Events
     VARIABLES { hpIpfEvtDetailStr }
     DESCRIPTION
        "Memory FW detected errors below 1MB.  FW will not allow boot in this case, so memory FW will reinterleave and retest."

     --#SUMMARY "Insufficient memory for operation"
     --#ARGUMENTS {}
     --#SEVERITY WARNING
     --#TIMEINDEX 100
     --#STATE OPERATIONAL
::= 5185


hpevtMemErrAddrNotInMbat TRAP-TYPE
     ENTERPRISE hpIpfE0Events
     VARIABLES { hpIpfEvtDetailStr }
     DESCRIPTION
        "Memory FW could not figure out which rank maps to the physical address specified in the data field."

     --#SUMMARY "Memory address not found in MBAT"
     --#ARGUMENTS {}
     --#SEVERITY WARNING
     --#TIMEINDEX 100
     --#STATE OPERATIONAL
::= 5186


hpevtMemErrClearFail TRAP-TYPE
     ENTERPRISE hpIpfE0Events
     VARIABLES { hpIpfEvtDetailStr }
     DESCRIPTION
        "Memory FW was unable to clear the platform error logs on the CEC.  The Datafield contains the error status of the CEC."

     --#SUMMARY "Memory Error Information not cleared"
     --#ARGUMENTS {}
     --#SEVERITY WARNING
     --#TIMEINDEX 100
     --#STATE OPERATIONAL
::= 5187


hpevtMemErrLogFailedToClear TRAP-TYPE
     ENTERPRISE hpIpfE0Events
     VARIABLES { hpIpfEvtDetailStr }
     DESCRIPTION
        "Memory FW was unable to clear the platform error logs on the CEC.  The Datafield contains the error status of the CEC."

     --#SUMMARY "Couldn't clear memory error logs"
     --#ARGUMENTS {}
     --#SEVERITY WARNING
     --#TIMEINDEX 100
     --#STATE OPERATIONAL
::= 5189


hpevtMemErrorRegClearFailure TRAP-TYPE
     ENTERPRISE hpIpfE0Events
     VARIABLES { hpIpfEvtDetailStr }
     DESCRIPTION
        "The Error registers in the CEC have failed to clear.  The data field contains the error status of the CEC after the attempted clear."

     --#SUMMARY "Memory error clear failed"
     --#ARGUMENTS {}
     --#SEVERITY WARNING
     --#TIMEINDEX 100
     --#STATE OPERATIONAL
::= 5190


hpevtMemExtFatalLoadOrdErr TRAP-TYPE
     ENTERPRISE hpIpfE0Events
     VARIABLES { hpIpfEvtDetailStr }
     DESCRIPTION
        "A DIMM that is required to be loaded in order for this DIMM to function properly is not loaded, so FW will deallocate this DIMM.  Currently, none of the platforms require any DIMMs to be loaded in order for this DIMM to work properly."

     --#SUMMARY "DIMM loading order error:  DIMM deallocated"
     --#ARGUMENTS {}
     --#SEVERITY WARNING
     --#TIMEINDEX 100
     --#STATE OPERATIONAL
::= 5191


hpevtMemFirmwareProb TRAP-TYPE
     ENTERPRISE hpIpfE0Events
     VARIABLES { hpIpfEvtDetailStr }
     DESCRIPTION
        "An error occurred that memory FW does not know how to handle."

     --#SUMMARY "Generic memory firmware error"
     --#ARGUMENTS {}
     --#SEVERITY WARNING
     --#TIMEINDEX 100
     --#STATE OPERATIONAL
::= 5193


hpevtMemInterleaveCodeFailure TRAP-TYPE
     ENTERPRISE hpIpfE0Events
     VARIABLES { hpIpfEvtDetailStr }
     DESCRIPTION
        "The memory interleaving code failed."

     --#SUMMARY "Memory interleaving algorithm failed"
     --#ARGUMENTS {}
     --#SEVERITY CRITICAL
     --#TIMEINDEX 100
     --#STATE OPERATIONAL
::= 5199


hpevtMemMainMemFailed TRAP-TYPE
     ENTERPRISE hpIpfE0Events
     VARIABLES { hpIpfEvtDetailStr }
     DESCRIPTION
        "FW was unable to create a memory configuration with no errors in low memory to hand off to EFI."

     --#SUMMARY "Memory interleave generation failed"
     --#ARGUMENTS {}
     --#SEVERITY CRITICAL
     --#TIMEINDEX 100
     --#STATE OPERATIONAL
::= 5202


hpevtMemMbeInRank TRAP-TYPE
     ENTERPRISE hpIpfE0Events
     VARIABLES { hpIpfEvtDetailStr }
     DESCRIPTION
        "A series of MEM_MBE_IN_RANK chassis code will be sent when an error is detected by firmware.  The data fields will contain information on the error based on the data type as follows:  Physical Location - location of dimm(s) in error;  Physical Address - address affect by error;  Syndrome - Firmware generated ECC syndrome that can be used to further isolate the error."

     --#SUMMARY "Uncorrectable (multiple-bit) ECC error in DIMM"
     --#ARGUMENTS {}
     --#SEVERITY WARNING
     --#TIMEINDEX 100
     --#STATE OPERATIONAL
::= 5204


hpevtMemMcRegFailure TRAP-TYPE
     ENTERPRISE hpIpfE0Events
     VARIABLES { hpIpfEvtDetailStr }
     DESCRIPTION
        "The chipset's memory controller failed the register test.  The data field contains the address of the register that failed selftest."

     --#SUMMARY "Memory register test failed"
     --#ARGUMENTS {}
     --#SEVERITY WARNING
     --#TIMEINDEX 100
     --#STATE OPERATIONAL
::= 5205


hpevtMemNoDimmsInstalled TRAP-TYPE
     ENTERPRISE hpIpfE0Events
     VARIABLES { hpIpfEvtDetailStr }
     DESCRIPTION
        "Memory Discovery could not detect any DIMMs installed."

     --#SUMMARY "SPD found no memory DIMMs"
     --#ARGUMENTS {}
     --#SEVERITY CRITICAL
     --#TIMEINDEX 100
     --#STATE OPERATIONAL
::= 5208


hpevtMemNoMemFound TRAP-TYPE
     ENTERPRISE hpIpfE0Events
     VARIABLES { hpIpfEvtDetailStr }
     DESCRIPTION
        "FW could not continue because there are no valid memory ranks loaded."

     --#SUMMARY "No memory found"
     --#ARGUMENTS {}
     --#SEVERITY CRITICAL
     --#TIMEINDEX 100
     --#STATE OPERATIONAL
::= 5209


hpevtMemPdtDisabledHalt TRAP-TYPE
     ENTERPRISE hpIpfE0Events
     VARIABLES { hpIpfEvtDetailStr }
     DESCRIPTION
        "The PDT has been disabled, and FW found memory errors during selftest.  This is a stopboot condition.  Also, the PDT will never be disabled in customer systems, so this event should never be seen in the field."

     --#SUMMARY "Cannot log memory error because PDT is disabled"
     --#ARGUMENTS {}
     --#SEVERITY CRITICAL
     --#TIMEINDEX 100
     --#STATE OPERATIONAL
::= 5211


hpevtMemPdtDisabledWarning TRAP-TYPE
     ENTERPRISE hpIpfE0Events
     VARIABLES { hpIpfEvtDetailStr }
     DESCRIPTION
        "An event indicating that the user has the PDT disabled on this boot.  The PDT will never be disabled in customer systems, so this event should never be seen in the field."

     --#SUMMARY "PDT is disabled"
     --#ARGUMENTS {}
     --#SEVERITY WARNING
     --#TIMEINDEX 100
     --#STATE OPERATIONAL
::= 5212


hpevtMemPdtNvmErr TRAP-TYPE
     ENTERPRISE hpIpfE0Events
     VARIABLES { hpIpfEvtDetailStr }
     DESCRIPTION
        "Error writing entry into the PDT."

     --#SUMMARY "Error adding entry to PDT"
     --#ARGUMENTS {}
     --#SEVERITY WARNING
     --#TIMEINDEX 100
     --#STATE OPERATIONAL
::= 5214


hpevtMemPdtTableFull TRAP-TYPE
     ENTERPRISE hpIpfE0Events
     VARIABLES { hpIpfEvtDetailStr }
     DESCRIPTION
        "An attempt was made to add an entry to a full PDT.  The entry is not added, and this event is sent."

     --#SUMMARY "Cannot add PDT entry-PDT full"
     --#ARGUMENTS {}
     --#SEVERITY CRITICAL
     --#TIMEINDEX 100
     --#STATE OPERATIONAL
::= 5216


hpevtMemPlatformInitFailure TRAP-TYPE
     ENTERPRISE hpIpfE0Events
     VARIABLES { hpIpfEvtDetailStr }
     DESCRIPTION
        "Memory FW was unable to save or restore the original error configuration (including CEC error log and signal enable and CPU ECC detection).  This event should never be seen in the field unless there is a FW problem"

     --#SUMMARY "Memory platform data update failure"
     --#ARGUMENTS {}
     --#SEVERITY WARNING
     --#TIMEINDEX 100
     --#STATE OPERATIONAL
::= 5218


hpevtMemRankEntryNotFound TRAP-TYPE
     ENTERPRISE hpIpfE0Events
     VARIABLES { hpIpfEvtDetailStr }
     DESCRIPTION
        "The rank structure that corresponds to the rankID in the data field could not be found in the Rank table.  The Data field is the rankID of the structure it is looking for.  This error event should never be seen."

     --#SUMMARY "Can't find memory rank entry"
     --#ARGUMENTS {}
     --#SEVERITY WARNING
     --#TIMEINDEX 100
     --#STATE OPERATIONAL
::= 5219


hpevtMemTestExcessMcBits TRAP-TYPE
     ENTERPRISE hpIpfE0Events
     VARIABLES { hpIpfEvtDetailStr }
     DESCRIPTION
        "More than one error type was detected when only one error type was expected."

     --#SUMMARY "Memory error overflow:"
     --#ARGUMENTS {}
     --#SEVERITY WARNING
     --#TIMEINDEX 100
     --#STATE OPERATIONAL
::= 5237


hpevtMemTestFwdProgBitsInvalid TRAP-TYPE
     ENTERPRISE hpIpfE0Events
     VARIABLES { hpIpfEvtDetailStr }
     DESCRIPTION
        "The forward progress bits that memory FW uses to track state are invalid.  The data field is the fwd progress field."

     --#SUMMARY "Memory forward progress code invalid"
     --#ARGUMENTS {}
     --#SEVERITY WARNING
     --#TIMEINDEX 100
     --#STATE OPERATIONAL
::= 5238


hpevtMemTestStatusBitsInvalid TRAP-TYPE
     ENTERPRISE hpIpfE0Events
     VARIABLES { hpIpfEvtDetailStr }
     DESCRIPTION
        "The memory error status has bits set in it that indicate another non-memory error occurred.  The data field contains the CEC's error status."

     --#SUMMARY "Memory error status invalid"
     --#ARGUMENTS {}
     --#SEVERITY WARNING
     --#TIMEINDEX 100
     --#STATE OPERATIONAL
::= 5244


hpevtMemTestSummaryBitsInvalid TRAP-TYPE
     ENTERPRISE hpIpfE0Events
     VARIABLES { hpIpfEvtDetailStr }
     DESCRIPTION
        "The memory test summary bits are invalid.  The data field is the test summary bits."

     --#SUMMARY "Memory error summary bits invalid"
     --#ARGUMENTS {}
     --#SEVERITY WARNING
     --#TIMEINDEX 100
     --#STATE OPERATIONAL
::= 5245


hpevtMemUnexpectedMca TRAP-TYPE
     ENTERPRISE hpIpfE0Events
     VARIABLES { hpIpfEvtDetailStr }
     DESCRIPTION
        "Memory rank shadowing has been selected but is not supported by the revision of the memory controller."

     --#SUMMARY "Unexpected machine check during memory code"
     --#ARGUMENTS {}
     --#SEVERITY CRITICAL
     --#TIMEINDEX 100
     --#STATE OPERATIONAL
::= 5248


hpevtMemWarnDistributionCheckBypass TRAP-TYPE
     ENTERPRISE hpIpfE0Events
     VARIABLES { hpIpfEvtDetailStr }
     DESCRIPTION
        "The control bit to skip the DIMM distribution check is set and the DIMM distribution check was skipped. This bit should only be done in the factory and not in the field."

     --#SUMMARY "The DIMM distribution check was bypassed"
     --#ARGUMENTS {}
     --#SEVERITY WARNING
     --#TIMEINDEX 100
     --#STATE OPERATIONAL
::= 5250


hpevtMemWarnLoadingOrderBypass TRAP-TYPE
     ENTERPRISE hpIpfE0Events
     VARIABLES { hpIpfEvtDetailStr }
     DESCRIPTION
        "The control bit to skip the DIMM loading order check is set and the DIMM loading order check was skipped. This bit should only be done in the factory and not in the field."

     --#SUMMARY "The DIMM Loading Order check was bypassed"
     --#ARGUMENTS {}
     --#SEVERITY WARNING
     --#TIMEINDEX 100
     --#STATE OPERATIONAL
::= 5252


hpevtMemWarnLoopOnDestTest TRAP-TYPE
     ENTERPRISE hpIpfE0Events
     VARIABLES { hpIpfEvtDetailStr }
     DESCRIPTION
        "The control bit to loop on destructive memory test is set and the destructive memory tests are run continously. This bit should only be done in the factory and not in the field."

     --#SUMMARY "Looping on destructive memory tests"
     --#ARGUMENTS {}
     --#SEVERITY WARNING
     --#TIMEINDEX 100
     --#STATE OPERATIONAL
::= 5253


hpevtMemWarnSetCheckBypass TRAP-TYPE
     ENTERPRISE hpIpfE0Events
     VARIABLES { hpIpfEvtDetailStr }
     DESCRIPTION
        "The control bit to skip the DIMM set check is set and the DIMM set check was skipped. This bit should only be done in the factory and not in the field."

     --#SUMMARY "DIMM Set Check has been skipped"
     --#ARGUMENTS {}
     --#SEVERITY WARNING
     --#TIMEINDEX 100
     --#STATE OPERATIONAL
::= 5255


hpevtMemWarnSpdBypass TRAP-TYPE
     ENTERPRISE hpIpfE0Events
     VARIABLES { hpIpfEvtDetailStr }
     DESCRIPTION
        "The control bit to skip the DIMM SPD check is set and the checking of the DIMM SPD was skipped. This bit should only be done in the factory and not in the field."

     --#SUMMARY "Serial Presence Detect (SPD) has been skipped"
     --#ARGUMENTS {}
     --#SEVERITY WARNING
     --#TIMEINDEX 100
     --#STATE OPERATIONAL
::= 5256


hpevtMemWarnUsingAltConfig TRAP-TYPE
     ENTERPRISE hpIpfE0Events
     VARIABLES { hpIpfEvtDetailStr }
     DESCRIPTION
        "The control bit to load an alternate memory configuration is set and an alternate memory configuration has been loaded.  This bit should only be set in the factory and not in the field."

     --#SUMMARY "An Alternate Memory Config has been loaded into the system"
     --#ARGUMENTS {}
     --#SEVERITY WARNING
     --#TIMEINDEX 100
     --#STATE OPERATIONAL
::= 5257


hpevtOsInitNotRegistered TRAP-TYPE
     ENTERPRISE hpIpfE0Events
     VARIABLES { hpIpfEvtDetailStr }
     DESCRIPTION
        "The OS_INIT vector has not been registered"

     --#SUMMARY "OS INIT address not registered"
     --#ARGUMENTS {}
     --#SEVERITY WARNING
     --#TIMEINDEX 100
     --#STATE OPERATIONAL
::= 5260


hpevtOsMcaNotRegistered TRAP-TYPE
     ENTERPRISE hpIpfE0Events
     VARIABLES { hpIpfEvtDetailStr }
     DESCRIPTION
        "The OS_MCA vector has not been registered"

     --#SUMMARY "OS MCA address not registered"
     --#ARGUMENTS {}
     --#SEVERITY WARNING
     --#TIMEINDEX 100
     --#STATE OPERATIONAL
::= 5263


hpevtOsMcaUncorrectedMc TRAP-TYPE
     ENTERPRISE hpIpfE0Events
     VARIABLES { hpIpfEvtDetailStr }
     DESCRIPTION
        "An Uncorrected Machine Check has occurred"

     --#SUMMARY "OS MCA did not correct the Machine Check"
     --#ARGUMENTS {}
     --#SEVERITY WARNING
     --#TIMEINDEX 100
     --#STATE OPERATIONAL
::= 5264


hpevtPdhMiscRegFail TRAP-TYPE
     ENTERPRISE hpIpfE0Events
     VARIABLES { hpIpfEvtDetailStr }
     DESCRIPTION
        "A PDH register has failed."

     --#SUMMARY "Found bad miscellaneous register"
     --#ARGUMENTS {}
     --#SEVERITY CRITICAL
     --#TIMEINDEX 100
     --#STATE OPERATIONAL
::= 5266


hpevtSalCheckUnknownFail TRAP-TYPE
     ENTERPRISE hpIpfE0Events
     VARIABLES { hpIpfEvtDetailStr }
     DESCRIPTION
        "The handler for SAL_CHECK has failed for an unknown reason."

     --#SUMMARY "SAL_CHECK failed for an unknown reason"
     --#ARGUMENTS {}
     --#SEVERITY WARNING
     --#TIMEINDEX 100
     --#STATE OPERATIONAL
::= 5268


hpevtSalInitUnknownFail TRAP-TYPE
     ENTERPRISE hpIpfE0Events
     VARIABLES { hpIpfEvtDetailStr }
     DESCRIPTION
        "The handler for SAL_INIT has failed for an unknown reason."

     --#SUMMARY "SAL_INIT failed for an unknown reason"
     --#ARGUMENTS {}
     --#SEVERITY WARNING
     --#TIMEINDEX 100
     --#STATE OPERATIONAL
::= 5270


hpevtUndefinedSmcInterleaveErr TRAP-TYPE
     ENTERPRISE hpIpfE0Events
     VARIABLES { hpIpfEvtDetailStr }
     DESCRIPTION
        "Indicates that FW encountered a Fatal interleaving error.  The data field contains the return status from the interleaving procedure call."

     --#SUMMARY "Unspecified memory interleave error"
     --#ARGUMENTS {}
     --#SEVERITY WARNING
     --#TIMEINDEX 100
     --#STATE OPERATIONAL
::= 5278


hpevtUnexpectedRetToSalCheck TRAP-TYPE
     ENTERPRISE hpIpfE0Events
     VARIABLES { hpIpfEvtDetailStr }
     DESCRIPTION
        "Unexpected return to SAL_CHECK."

     --#SUMMARY "Unexpected return to SAL_CHECK"
     --#ARGUMENTS {}
     --#SEVERITY CRITICAL
     --#TIMEINDEX 100
     --#STATE OPERATIONAL
::= 5279


hpevtUnexpectedRetToSalInit TRAP-TYPE
     ENTERPRISE hpIpfE0Events
     VARIABLES { hpIpfEvtDetailStr }
     DESCRIPTION
        "The SFW TOC vector (SAL_INIT) has been unexpectedly returned to."

     --#SUMMARY "Unexpected return to SAL_INIT"
     --#ARGUMENTS {}
     --#SEVERITY CRITICAL
     --#TIMEINDEX 100
     --#STATE OPERATIONAL
::= 5280


hpevtFwInstalledCpuDegraded TRAP-TYPE
     ENTERPRISE hpIpfE0Events
     VARIABLES { hpIpfEvtDetailStr }
     DESCRIPTION
        "Firmware is adding a device tree node for a CPU that is degraded in functionality.  The cpu should not be trusted and will not be active in the system."

     --#SUMMARY "Firmware is adding a DEGRADED cpu node to the device tree."
     --#ARGUMENTS {}
     --#SEVERITY WARNING
     --#TIMEINDEX 100
     --#STATE OPERATIONAL
::= 5335


hpevtPdRendezTreeError TRAP-TYPE
     ENTERPRISE hpIpfE0Events
     VARIABLES { hpIpfEvtDetailStr }
     DESCRIPTION
        "Firmware was unable to locate a required element in the device tree and cannot create a partition.  The resource that cannot be located is listed as an ansii string in the data field."

     --#SUMMARY "PD rendezvous will fail do to a Firmware Tree error"
     --#ARGUMENTS {}
     --#SEVERITY CRITICAL
     --#TIMEINDEX 100
     --#STATE OPERATIONAL
::= 5354


hpevtPdCellConfigError TRAP-TYPE
     ENTERPRISE hpIpfE0Events
     VARIABLES { hpIpfEvtDetailStr }
     DESCRIPTION
        "The currently executing cell is not configured to be part of the cell set it is attempting to rendezvous with."

     --#SUMMARY "The current cell is not configured as part of the expected set"
     --#ARGUMENTS {}
     --#SEVERITY CRITICAL
     --#TIMEINDEX 100
     --#STATE OPERATIONAL
::= 5359


hpevtPdRemoteCsrReadError TRAP-TYPE
     ENTERPRISE hpIpfE0Events
     VARIABLES { hpIpfEvtDetailStr }
     DESCRIPTION
        "The current cell could not read a remote cells CSR.  The remote cell number is displayed in the data field.  These cells will not be able to rendezvous."

     --#SUMMARY "A remote CSR could not be read"
     --#ARGUMENTS {}
     --#SEVERITY CRITICAL
     --#TIMEINDEX 100
     --#STATE OPERATIONAL
::= 5360


hpevtPdCellLateForRendez TRAP-TYPE
     ENTERPRISE hpIpfE0Events
     VARIABLES { hpIpfEvtDetailStr }
     DESCRIPTION
        "The currently executing cell arrived too late to rendezvous with the other cells described in the complex profile as cells it should rendezvous with."

     --#SUMMARY "The current cell is too late to rendezvous with other cells"
     --#ARGUMENTS {}
     --#SEVERITY CRITICAL
     --#TIMEINDEX 100
     --#STATE OPERATIONAL
::= 5361


hpevtPdIncompatibleCpuTypes TRAP-TYPE
     ENTERPRISE hpIpfE0Events
     VARIABLES { hpIpfEvtDetailStr }
     DESCRIPTION
        "The currently executing cell detected CPUs that are incompatible with it to be installed on a cell that the current cell is trying to rendezvous with."

     --#SUMMARY "The current cell detected incompatible CPUs on another cell"
     --#ARGUMENTS {}
     --#SEVERITY CRITICAL
     --#TIMEINDEX 100
     --#STATE OPERATIONAL
::= 5365


hpevtPdCellLateLocalRendezSet TRAP-TYPE
     ENTERPRISE hpIpfE0Events
     VARIABLES { hpIpfEvtDetailStr }
     DESCRIPTION
        "The current cell was too slow creating the local rendezvous set and the other cells have left it behind.  It will not be able to participate in the remainder of the rendezvous.  The data field is unused, but the cell emitting this event is the one too late to rendevous."

     --#SUMMARY "Current cell was too slow creating the local rendezvous set"
     --#ARGUMENTS {}
     --#SEVERITY CRITICAL
     --#TIMEINDEX 100
     --#STATE OPERATIONAL
::= 5366


hpevtCellNotInGlobalSet TRAP-TYPE
     ENTERPRISE hpIpfE0Events
     VARIABLES { hpIpfEvtDetailStr }
     DESCRIPTION
        "The reporting cell was not included in the final global set that was agreed upon.  This means that another cell either could not reach the reporting cell or the reporting cell was too late ariving to a required state."

     --#SUMMARY "Reporting cell was not included in the global cell set"
     --#ARGUMENTS {}
     --#SEVERITY CRITICAL
     --#TIMEINDEX 100
     --#STATE OPERATIONAL
::= 5376


hpevtNoViableCoreCellInPd TRAP-TYPE
     ENTERPRISE hpIpfE0Events
     VARIABLES { hpIpfEvtDetailStr }
     DESCRIPTION
        "No cells in the PD can be a core cell.  This is fatal."

     --#SUMMARY "No Core Cell can be selected in the PD."
     --#ARGUMENTS {}
     --#SEVERITY CRITICAL
     --#TIMEINDEX 100
     --#STATE OPERATIONAL
::= 5380


hpevtErrorPromotingCoreCell TRAP-TYPE
     ENTERPRISE hpIpfE0Events
     VARIABLES { hpIpfEvtDetailStr }
     DESCRIPTION
        "System Firmware was unable to notify utilities of the selected core cell number."

     --#SUMMARY "Firmware was unable to notify utilities of the core cell number"
     --#ARGUMENTS {}
     --#SEVERITY CRITICAL
     --#TIMEINDEX 100
     --#STATE OPERATIONAL
::= 5383


hpevtFabricNoServiceProviders TRAP-TYPE
     ENTERPRISE hpIpfE0Events
     VARIABLES { hpIpfEvtDetailStr }
     DESCRIPTION
        "The fabric code is unable to find a service provider for a required banyan service."

     --#SUMMARY "Fabric code unable to find a needed service provider."
     --#ARGUMENTS {}
     --#SEVERITY CRITICAL
     --#TIMEINDEX 100
     --#STATE OPERATIONAL
::= 5403


hpevtFabricPortError TRAP-TYPE
     ENTERPRISE hpIpfE0Events
     VARIABLES { hpIpfEvtDetailStr }
     DESCRIPTION
        "The fabric port specified in the data field had an error."

     --#SUMMARY "Error in a fabric Port"
     --#ARGUMENTS {}
     --#SEVERITY WARNING
     --#TIMEINDEX 100
     --#STATE OPERATIONAL
::= 5404


hpevtFabricReadError TRAP-TYPE
     ENTERPRISE hpIpfE0Events
     VARIABLES { hpIpfEvtDetailStr }
     DESCRIPTION
        "An error occurred reading a CSR.  The CSR address is displayed in the data field."

     --#SUMMARY "Parity error detected on read from fabric"
     --#ARGUMENTS {}
     --#SEVERITY WARNING
     --#TIMEINDEX 100
     --#STATE OPERATIONAL
::= 5405


hpevtFabricWriteError TRAP-TYPE
     ENTERPRISE hpIpfE0Events
     VARIABLES { hpIpfEvtDetailStr }
     DESCRIPTION
        "Error writing to Fabric.  CSR data in data field."

     --#SUMMARY "Error writing to Fabric"
     --#ARGUMENTS {}
     --#SEVERITY WARNING
     --#TIMEINDEX 100
     --#STATE OPERATIONAL
::= 5406


hpevtXbcSlicesHwVersionDiffer TRAP-TYPE
     ENTERPRISE hpIpfE0Events
     VARIABLES { hpIpfEvtDetailStr }
     DESCRIPTION
        "Incompatible crossbar slices are installed  The data field is the two revisions reported by slice1 and slice0 of the CSR data.
Bits [31:0] slice0 revision
Bits [63:32] slice1 revision"

     --#SUMMARY "Crossbar slices are out of rev with each other."
     --#ARGUMENTS {}
     --#SEVERITY CRITICAL
     --#TIMEINDEX 100
     --#STATE OPERATIONAL
::= 5407


hpevtXbcSlicesInDiffLocation TRAP-TYPE
     ENTERPRISE hpIpfE0Events
     VARIABLES { hpIpfEvtDetailStr }
     DESCRIPTION
        "Crossbar slices are in different locations.  The data field is the two locations reported by slice1 and slice0 of the CSR data."

     --#SUMMARY "Crossbar slices are configured poorly"
     --#ARGUMENTS {}
     --#SEVERITY CRITICAL
     --#TIMEINDEX 100
     --#STATE OPERATIONAL
::= 5408


hpevtMonarchTakeover TRAP-TYPE
     ENTERPRISE hpIpfE0Events
     VARIABLES { hpIpfEvtDetailStr }
     DESCRIPTION
        "A CPU has taken over as the monarch CPU."

     --#SUMMARY "A CPU has taken over for the monarch CPU"
     --#ARGUMENTS {}
     --#SEVERITY CRITICAL
     --#TIMEINDEX 100
     --#STATE OPERATIONAL
::= 5411


hpevtDeadSram TRAP-TYPE
     ENTERPRISE hpIpfE0Events
     VARIABLES { hpIpfEvtDetailStr }
     DESCRIPTION
        "SRAM cannot be accessed on the cell board.  Execution cannot continue."

     --#SUMMARY "Sram cannot be used on the cell"
     --#ARGUMENTS {}
     --#SEVERITY CRITICAL
     --#TIMEINDEX 100
     --#STATE OPERATIONAL
::= 5416


hpevtDeadDillon TRAP-TYPE
     ENTERPRISE hpIpfE0Events
     VARIABLES { hpIpfEvtDetailStr }
     DESCRIPTION
        "The PDH Arbiter component/chip cannot be located or used."

     --#SUMMARY "The dillon hardware cannot be located."
     --#ARGUMENTS {}
     --#SEVERITY CRITICAL
     --#TIMEINDEX 100
     --#STATE OPERATIONAL
::= 5417


hpevtDeadPdhHw TRAP-TYPE
     ENTERPRISE hpIpfE0Events
     VARIABLES { hpIpfEvtDetailStr }
     DESCRIPTION
        "A required piece of PDH bus hardware cannot be contacted."

     --#SUMMARY "A required piece of PDH bus hardware cannot be contacted."
     --#ARGUMENTS {}
     --#SEVERITY CRITICAL
     --#TIMEINDEX 100
     --#STATE OPERATIONAL
::= 5418


hpevtIoPciBusMixedSpeeds TRAP-TYPE
     ENTERPRISE hpIpfE0Events
     VARIABLES { hpIpfEvtDetailStr }
     DESCRIPTION
        "The physical location of the PCI controller with mixed speeds is displayed in the data field."

     --#SUMMARY "Error: PCI Buses are configured for multiple speeds"
     --#ARGUMENTS {}
     --#SEVERITY WARNING
     --#TIMEINDEX 100
     --#STATE OPERATIONAL
::= 5419


hpevtIoPciBusDepthExceeded TRAP-TYPE
     ENTERPRISE hpIpfE0Events
     VARIABLES { hpIpfEvtDetailStr }
     DESCRIPTION
        "During walking of the IO busses, the maximum depth was exceeded.  This is a hardware configuration problem.  The data field contains the physical location."

     --#SUMMARY "The bus depth was exceeded during IO probing."
     --#ARGUMENTS {}
     --#SEVERITY CRITICAL
     --#TIMEINDEX 100
     --#STATE OPERATIONAL
::= 5420


hpevtlotimeout TRAP-TYPE
     ENTERPRISE hpIpfE0Events
     VARIABLES { hpIpfEvtDetailStr }
     DESCRIPTION
        "A Timeout occurred during RI initialization.  The CSR is in the data field.  The alert level will vary."

     --#SUMMARY "A Timeout occurred during RI initialization.  The CSR is in the data field.  The alert level will vary."
     --#ARGUMENTS {}
     --#SEVERITY CRITICAL
     --#TIMEINDEX 100
     --#STATE OPERATIONAL
::= 5432


hpevtIoBuswalkSuperio TRAP-TYPE
     ENTERPRISE hpIpfE0Events
     VARIABLES { hpIpfEvtDetailStr }
     DESCRIPTION
        "SuperIO has been detected in the PCI slot displayed in the data field."

     --#SUMMARY "SuperIO has been detected in slot"
     --#ARGUMENTS {}
     --#SEVERITY WARNING
     --#TIMEINDEX 100
     --#STATE OPERATIONAL
::= 5438


hpevtIoSbaCorrDataParityErr TRAP-TYPE
     ENTERPRISE hpIpfE0Events
     VARIABLES { hpIpfEvtDetailStr }
     DESCRIPTION
        "IO Link Software error was corrected."

     --#SUMMARY "IO Link software error was corrected."
     --#ARGUMENTS {}
     --#SEVERITY WARNING
     --#TIMEINDEX 100
     --#STATE OPERATIONAL
::= 5440


hpevtIoSbaFatalDataParityErr TRAP-TYPE
     ENTERPRISE hpIpfE0Events
     VARIABLES { hpIpfEvtDetailStr }
     DESCRIPTION
        "Parity error in Reg FIFO Internal parity error."

     --#SUMMARY "Parity error in Reg FIFO Internal parity error."
     --#ARGUMENTS {}
     --#SEVERITY CRITICAL
     --#TIMEINDEX 100
     --#STATE OPERATIONAL
::= 5442


hpevtIoSbaUncFunctionErr TRAP-TYPE
     ENTERPRISE hpIpfE0Events
     VARIABLES { hpIpfEvtDetailStr }
     DESCRIPTION
        "TLB Fetch timeout."

     --#SUMMARY "TLB Fetch timeout"
     --#ARGUMENTS {}
     --#SEVERITY CRITICAL
     --#TIMEINDEX 100
     --#STATE OPERATIONAL
::= 5443


hpevtIoSbaFatalFunctionErr TRAP-TYPE
     ENTERPRISE hpIpfE0Events
     VARIABLES { hpIpfEvtDetailStr }
     DESCRIPTION
        "Link presence goes away, FE."

     --#SUMMARY "Link presence goes away, FE"
     --#ARGUMENTS {}
     --#SEVERITY CRITICAL
     --#TIMEINDEX 100
     --#STATE OPERATIONAL
::= 5444


hpevtIoSbaFatalParityErr TRAP-TYPE
     ENTERPRISE hpIpfE0Events
     VARIABLES { hpIpfEvtDetailStr }
     DESCRIPTION
        "LBA to SBA parity error on command, rope will go fatal."

     --#SUMMARY "Elroy to REO parity error on command, rope will go fatal"
     --#ARGUMENTS {}
     --#SEVERITY CRITICAL
     --#TIMEINDEX 100
     --#STATE OPERATIONAL
::= 5445


hpevtIoSbaFatalMapErr TRAP-TYPE
     ENTERPRISE hpIpfE0Events
     VARIABLES { hpIpfEvtDetailStr }
     DESCRIPTION
        "Access to invalid TLB entry Requesting rope fatal."

     --#SUMMARY "Access to invalid TLB entry Requesting rope fatal"
     --#ARGUMENTS {}
     --#SEVERITY CRITICAL
     --#TIMEINDEX 100
     --#STATE OPERATIONAL
::= 5446


hpevtIoSbaFatalTimeoutErr TRAP-TYPE
     ENTERPRISE hpIpfE0Events
     VARIABLES { hpIpfEvtDetailStr }
     DESCRIPTION
        "Memory Fetch Timeout."

     --#SUMMARY "Memory fetch timeout"
     --#ARGUMENTS {}
     --#SEVERITY CRITICAL
     --#TIMEINDEX 100
     --#STATE OPERATIONAL
::= 5447


hpevtIoLbaInitErr TRAP-TYPE
     ENTERPRISE hpIpfE0Events
     VARIABLES { hpIpfEvtDetailStr }
     DESCRIPTION
        "An error was encountered when initing the rope number specified in the data field."

     --#SUMMARY "Error was encountered when Initializion the LBA."
     --#ARGUMENTS {}
     --#SEVERITY CRITICAL
     --#TIMEINDEX 100
     --#STATE OPERATIONAL
::= 5448


hpevtIoLbaCorrTimeoutErr TRAP-TYPE
     ENTERPRISE hpIpfE0Events
     VARIABLES { hpIpfEvtDetailStr }
     DESCRIPTION
        "LBA correctable timeout error was encountered."

     --#SUMMARY "LBA correctable Timeout Error was encountered."
     --#ARGUMENTS {}
     --#SEVERITY WARNING
     --#TIMEINDEX 100
     --#STATE OPERATIONAL
::= 5449


hpevtIoLbaUncFunctionErr TRAP-TYPE
     ENTERPRISE hpIpfE0Events
     VARIABLES { hpIpfEvtDetailStr }
     DESCRIPTION
        "LBA uncorrectable Function Error was encountered."

     --#SUMMARY "LBA uncorrectable Function Error was encountered."
     --#ARGUMENTS {}
     --#SEVERITY CRITICAL
     --#TIMEINDEX 100
     --#STATE OPERATIONAL
::= 5450


hpevtIoLbaUncTimeoutErr TRAP-TYPE
     ENTERPRISE hpIpfE0Events
     VARIABLES { hpIpfEvtDetailStr }
     DESCRIPTION
        "LBA uncorrectable Timeout Error was encountered."

     --#SUMMARY "LBA uncorrectable Timeout Error was encountered."
     --#ARGUMENTS {}
     --#SEVERITY CRITICAL
     --#TIMEINDEX 100
     --#STATE OPERATIONAL
::= 5451


hpevtIoLbaMiscUncErr TRAP-TYPE
     ENTERPRISE hpIpfE0Events
     VARIABLES { hpIpfEvtDetailStr }
     DESCRIPTION
        "Misc uncorrectable error discovered on LBA."

     --#SUMMARY "Misc. uncorrectable error discovered on LBA."
     --#ARGUMENTS {}
     --#SEVERITY CRITICAL
     --#TIMEINDEX 100
     --#STATE OPERATIONAL
::= 5452


hpevtIoLbaUncParityErr TRAP-TYPE
     ENTERPRISE hpIpfE0Events
     VARIABLES { hpIpfEvtDetailStr }
     DESCRIPTION
        "LBA encountered an uncorrectable parity error."

     --#SUMMARY "LBA encountered an uncorrectable parity error."
     --#ARGUMENTS {}
     --#SEVERITY CRITICAL
     --#TIMEINDEX 100
     --#STATE OPERATIONAL
::= 5453


hpevtIoLbaMiscFatalErr TRAP-TYPE
     ENTERPRISE hpIpfE0Events
     VARIABLES { hpIpfEvtDetailStr }
     DESCRIPTION
        "LBA misc. Fatal Error encountered."

     --#SUMMARY "LBA Misc. Fatal Error encountered."
     --#ARGUMENTS {}
     --#SEVERITY CRITICAL
     --#TIMEINDEX 100
     --#STATE OPERATIONAL
::= 5454


hpevtIoLbaFatalFunctionErr TRAP-TYPE
     ENTERPRISE hpIpfE0Events
     VARIABLES { hpIpfEvtDetailStr }
     DESCRIPTION
        "LBA Fatal function error encountered."

     --#SUMMARY "LBA Fatal function error encountered."
     --#ARGUMENTS {}
     --#SEVERITY CRITICAL
     --#TIMEINDEX 100
     --#STATE OPERATIONAL
::= 5455


hpevtIoLbaFatalParityErr TRAP-TYPE
     ENTERPRISE hpIpfE0Events
     VARIABLES { hpIpfEvtDetailStr }
     DESCRIPTION
        "LBA Fatal Parity error encountered."

     --#SUMMARY "LBA Fatal Parity error encountered."
     --#ARGUMENTS {}
     --#SEVERITY CRITICAL
     --#TIMEINDEX 100
     --#STATE OPERATIONAL
::= 5456


hpevtIoLbaFatalTimeoutErr TRAP-TYPE
     ENTERPRISE hpIpfE0Events
     VARIABLES { hpIpfEvtDetailStr }
     DESCRIPTION
        "LBA Fatal timeout error encountered."

     --#SUMMARY "LBA Fatal Timeout Error Encountered."
     --#ARGUMENTS {}
     --#SEVERITY CRITICAL
     --#TIMEINDEX 100
     --#STATE OPERATIONAL
::= 5457


hpevtIoDevAdapterMiscUncErr TRAP-TYPE
     ENTERPRISE hpIpfE0Events
     VARIABLES { hpIpfEvtDetailStr }
     DESCRIPTION
        "Misc Uncorrectable Error encountered on the card specified in the data field."

     --#SUMMARY "Misc Uncorrectable Error encountered."
     --#ARGUMENTS {}
     --#SEVERITY CRITICAL
     --#TIMEINDEX 100
     --#STATE OPERATIONAL
::= 5458


hpevtIoDevAdapterMiscFatalErr TRAP-TYPE
     ENTERPRISE hpIpfE0Events
     VARIABLES { hpIpfEvtDetailStr }
     DESCRIPTION
        "Misc fatal error was discovered on the PCI card specified in the data field."

     --#SUMMARY "Misc fatal error discovered on PCI card"
     --#ARGUMENTS {}
     --#SEVERITY CRITICAL
     --#TIMEINDEX 100
     --#STATE OPERATIONAL
::= 5459


hpevtMemDimmSpdExtendedChecksum TRAP-TYPE
     ENTERPRISE hpIpfE0Events
     VARIABLES { hpIpfEvtDetailStr }
     DESCRIPTION
        "The calculated and compared Checksums of the SPD EEPROM don't match."

     --#SUMMARY "DIMM SPD Extended Checksum Failure"
     --#ARGUMENTS {}
     --#SEVERITY CRITICAL
     --#TIMEINDEX 100
     --#STATE OPERATIONAL
::= 5464


hpevtOptsHdrCksumError TRAP-TYPE
     ENTERPRISE hpIpfE0Events
     VARIABLES { hpIpfEvtDetailStr }
     DESCRIPTION
        "The Options component encountered a header checksum error.  The actual data is in the data field of the chassis code."

     --#SUMMARY "Options header checksum error encountered."
     --#ARGUMENTS {}
     --#SEVERITY WARNING
     --#TIMEINDEX 100
     --#STATE OPERATIONAL
::= 5467


hpevtOptsDataCksumError TRAP-TYPE
     ENTERPRISE hpIpfE0Events
     VARIABLES { hpIpfEvtDetailStr }
     DESCRIPTION
        "The Options service data had a bad checksum.  Actual data is in the data field."

     --#SUMMARY "Options data checksum error was encountered."
     --#ARGUMENTS {}
     --#SEVERITY WARNING
     --#TIMEINDEX 100
     --#STATE OPERATIONAL
::= 5468


hpevtPdMemIntlvWaysMismatch TRAP-TYPE
     ENTERPRISE hpIpfE0Events
     VARIABLES { hpIpfEvtDetailStr }
     DESCRIPTION
        "Internal inconsistancy in the interleave tables."

     --#SUMMARY "Internal inconsistancy in the interleave tables."
     --#ARGUMENTS {}
     --#SEVERITY CRITICAL
     --#TIMEINDEX 100
     --#STATE OPERATIONAL
::= 5473


hpevtPdMemUnintlvdMemory TRAP-TYPE
     ENTERPRISE hpIpfE0Events
     VARIABLES { hpIpfEvtDetailStr }
     DESCRIPTION
        "The CellInfoList is not null and was expected to be.  There has been an error in interleaving."

     --#SUMMARY "CellInfoList is not NULL."
     --#ARGUMENTS {}
     --#SEVERITY WARNING
     --#TIMEINDEX 100
     --#STATE OPERATIONAL
::= 5474


hpevtPdMemNoMemoryDesc TRAP-TYPE
     ENTERPRISE hpIpfE0Events
     VARIABLES { hpIpfEvtDetailStr }
     DESCRIPTION
        "Error in constructing the Memory Descriptor."

     --#SUMMARY "Error in constructing the Memory Descriptor."
     --#ARGUMENTS {}
     --#SEVERITY CRITICAL
     --#TIMEINDEX 100
     --#STATE OPERATIONAL
::= 5478


hpevtPdMemUpdateLocalCellFailed TRAP-TYPE
     ENTERPRISE hpIpfE0Events
     VARIABLES { hpIpfEvtDetailStr }
     DESCRIPTION
        "Unable to update the local memory layout."

     --#SUMMARY "Unable to update the local memory layout"
     --#ARGUMENTS {}
     --#SEVERITY CRITICAL
     --#TIMEINDEX 100
     --#STATE OPERATIONAL
::= 5479


hpevtPdMemPdtAddrNotFound TRAP-TYPE
     ENTERPRISE hpIpfE0Events
     VARIABLES { hpIpfEvtDetailStr }
     DESCRIPTION
        "A required address was not found within a mapped address in the PDT."

     --#SUMMARY "A required address was not found within a mapped address."
     --#ARGUMENTS {}
     --#SEVERITY CRITICAL
     --#TIMEINDEX 100
     --#STATE OPERATIONAL
::= 5483


hpevtPdMemPdtInstallFail TRAP-TYPE
     ENTERPRISE hpIpfE0Events
     VARIABLES { hpIpfEvtDetailStr }
     DESCRIPTION
        "Failure to install a partition level PDT.  Errors prevented it."

     --#SUMMARY "Failure to install a Partition level PDT."
     --#ARGUMENTS {}
     --#SEVERITY CRITICAL
     --#TIMEINDEX 100
     --#STATE OPERATIONAL
::= 5485


hpevtUnusableResource TRAP-TYPE
     ENTERPRISE hpIpfE0Events
     VARIABLES { hpIpfEvtDetailStr }
     DESCRIPTION
        "A critical resouse that is required early in the initialization process either could not be found, or was unusable.  The specific resouse is specified in the data field as follows:  Platform Paramaters Component not found in FIT: 0xdead0001; SRAM_BASE not found in platform parms: 0xdead0002; SRAM_SIZE not found in Platform Parms: 0xdead0003; firmware framework not found in the fit: 0xdead0004; Framework Segmant not usable: 0xdead0005; bad NVRAM: 0xdead0006; PDH Arbiter unusable: 0xdead0007; SRAM unusable: 0xdead0008; CPU unusable: 0xdead0009; Options Component Unusable: 0xdead000a; Real Time Clock unusable: DEAD_RTC; Unknown: 0xdead0086"

     --#SUMMARY "A critical resourse could not be found or is unusable"
     --#ARGUMENTS {}
     --#SEVERITY CRITICAL
     --#TIMEINDEX 100
     --#STATE OPERATIONAL
::= 5490


hpevtFwError TRAP-TYPE
     ENTERPRISE hpIpfE0Events
     VARIABLES { hpIpfEvtDetailStr }
     DESCRIPTION
        "An internal firmware error was encountered.  This is usually caused by a bad parameter passed to a function, corrupt memory, corrupt malloc tables or something similar.  The data field contains the IP address of the function that encountered the error."

     --#SUMMARY "Internal firmware programming error."
     --#ARGUMENTS {}
     --#SEVERITY CRITICAL
     --#TIMEINDEX 100
     --#STATE OPERATIONAL
::= 5491


hpevtNvramDataCmpError TRAP-TYPE
     ENTERPRISE hpIpfE0Events
     VARIABLES { hpIpfEvtDetailStr }
     DESCRIPTION
        "NVRAM failed with a data compare error.  3 chassis codes will be sent.  The first one will have the expected data and the second the actual data and the third one will be the address."

     --#SUMMARY "NVRam test failed with a data compare error"
     --#ARGUMENTS {}
     --#SEVERITY CRITICAL
     --#TIMEINDEX 100
     --#STATE OPERATIONAL
::= 5492


hpevtNvramCrcError TRAP-TYPE
     ENTERPRISE hpIpfE0Events
     VARIABLES { hpIpfEvtDetailStr }
     DESCRIPTION
        "An NVRAM CRC Error was detected.  There will always be 2 chassis codes sent.  The first one will give the expected data and the second the actual data."

     --#SUMMARY "An NVRam CRC Error was detected"
     --#ARGUMENTS {}
     --#SEVERITY CRITICAL
     --#TIMEINDEX 100
     --#STATE OPERATIONAL
::= 5493


hpevtErm TRAP-TYPE
     ENTERPRISE hpIpfE0Events
     VARIABLES { hpIpfEvtDetailStr }
     DESCRIPTION
        "Get Error Response Mode has been called.  The first 8 bytes of the response mode string are displayed in the data field and must be converted to ascii from the hex values."

     --#SUMMARY "The Error Response Mode has been determined"
     --#ARGUMENTS {}
     --#SEVERITY WARNING
     --#TIMEINDEX 100
     --#STATE OPERATIONAL
::= 5494


hpevtErrorObtainingSemaphore TRAP-TYPE
     ENTERPRISE hpIpfE0Events
     VARIABLES { hpIpfEvtDetailStr }
     DESCRIPTION
        "The required semaphore could not be obtained due to errors.  The data field contains the IP of the routine trying to obtain the semaphore.   
 
A request was placed for more NVRAM to be allocated but NVRAM was full."

     --#SUMMARY "A semaphore could not be obtained"
     --#ARGUMENTS {}
     --#SEVERITY CRITICAL
     --#TIMEINDEX 100
     --#STATE OPERATIONAL
::= 5496


hpevtNvramBlockRevMismatch TRAP-TYPE
     ENTERPRISE hpIpfE0Events
     VARIABLES { hpIpfEvtDetailStr }
     DESCRIPTION
        "The NVRAM block requested has an unexpected revision.  This chassis code will be emmitted in pairs.  The first one will contain the expected revision number, the second will contain the actual revision number."

     --#SUMMARY "The BLOCK requested in NVRAM has the wrong revision"
     --#ARGUMENTS {}
     --#SEVERITY CRITICAL
     --#TIMEINDEX 100
     --#STATE OPERATIONAL
::= 5498


hpevtNvramBlockNotFound TRAP-TYPE
     ENTERPRISE hpIpfE0Events
     VARIABLES { hpIpfEvtDetailStr }
     DESCRIPTION
        "The requested NVRAM block was not found.  The ID that was not found is displayed in the data field."

     --#SUMMARY "The requested NVRAM block was not found."
     --#ARGUMENTS {}
     --#SEVERITY WARNING
     --#TIMEINDEX 100
     --#STATE OPERATIONAL
::= 5499


hpevtNvramBlockLocked TRAP-TYPE
     ENTERPRISE hpIpfE0Events
     VARIABLES { hpIpfEvtDetailStr }
     DESCRIPTION
        "The block id specified in the data field is locked."

     --#SUMMARY "The requested NVRAM block is locked."
     --#ARGUMENTS {}
     --#SEVERITY WARNING
     --#TIMEINDEX 100
     --#STATE OPERATIONAL
::= 5500


hpevtNvramBlockUnlocked TRAP-TYPE
     ENTERPRISE hpIpfE0Events
     VARIABLES { hpIpfEvtDetailStr }
     DESCRIPTION
        "Firmware tried to unlock a NVRAM block that was already unlocked.  Data field contains the block ID."

     --#SUMMARY "Firmware tried to unlock a NVRAM block that was already unlocked."
     --#ARGUMENTS {}
     --#SEVERITY WARNING
     --#TIMEINDEX 100
     --#STATE OPERATIONAL
::= 5501


hpevtNvramHeaderNotFound TRAP-TYPE
     ENTERPRISE hpIpfE0Events
     VARIABLES { hpIpfEvtDetailStr }
     DESCRIPTION
        "The header in the NVRAM space was not found."

     --#SUMMARY "The Header in NVRAM was not found"
     --#ARGUMENTS {}
     --#SEVERITY CRITICAL
     --#TIMEINDEX 100
     --#STATE OPERATIONAL
::= 5502


hpevtNvmFreelistCorrupt TRAP-TYPE
     ENTERPRISE hpIpfE0Events
     VARIABLES { hpIpfEvtDetailStr }
     DESCRIPTION
        "The Freelist used vor Non-Volatile Memory allocation is corrpt."

     --#SUMMARY "The Freelist used for NVM block allocation is corrupt."
     --#ARGUMENTS {}
     --#SEVERITY CRITICAL
     --#TIMEINDEX 100
     --#STATE OPERATIONAL
::= 5503


hpevtResetForReconfig TRAP-TYPE
     ENTERPRISE hpIpfE0Events
     VARIABLES { hpIpfEvtDetailStr }
     DESCRIPTION
        "System firmware has detected a condition that requires the cell to be reset for reconfiguration.  The function has been called and is now executing.  Data field contains the cell number being reset."

     --#SUMMARY "Firmware is preparing to reset for reconfiguration."
     --#ARGUMENTS {}
     --#SEVERITY CRITICAL
     --#TIMEINDEX 100
     --#STATE OPERATIONAL
::= 5505


hpevtPdRendezUtilityError TRAP-TYPE
     ENTERPRISE hpIpfE0Events
     VARIABLES { hpIpfEvtDetailStr }
     DESCRIPTION
        "During PD rendezvous, system firmware encountered a problem sending commands to the utilities system.  This will prevent a fully functional PD from being created."

     --#SUMMARY "An error was encountered communicating with  utilities during PD rendez."
     --#ARGUMENTS {}
     --#SEVERITY CRITICAL
     --#TIMEINDEX 100
     --#STATE OPERATIONAL
::= 5507


hpevtHalt TRAP-TYPE
     ENTERPRISE hpIpfE0Events
     VARIABLES { hpIpfEvtDetailStr }
     DESCRIPTION
        "System Firmware has determined that cell or system progress must be halted.  The data field contains the Instruction Pointer of the function that called for the halt.  The second instance of this code being emitted indicates the major state in system change.  This code must be emmitted in pairs."

     --#SUMMARY "Forward Progress is stopping.  The Cell or System will not boot further."
     --#ARGUMENTS {}
     --#SEVERITY CRITICAL
     --#TIMEINDEX 100
     --#STATE OPERATIONAL
::= 5509


hpevtDuiNoConsole TRAP-TYPE
     ENTERPRISE hpIpfE0Events
     VARIABLES { hpIpfEvtDetailStr }
     DESCRIPTION
        "The DUI (Developers User Interface) was entered, but there is no console available for the interface."

     --#SUMMARY "No console is available for the DUI to use."
     --#ARGUMENTS {}
     --#SEVERITY WARNING
     --#TIMEINDEX 100
     --#STATE OPERATIONAL
::= 5510


hpevtErrorProcFailed TRAP-TYPE
     ENTERPRISE hpIpfE0Events
     VARIABLES { hpIpfEvtDetailStr }
     DESCRIPTION
        "During Error processing and reporting, an error was detected that prevented further processing of errors.  The data field contains an ASCII message indicating the problem."

     --#SUMMARY "Error Processing encountered an unrecoverable error"
     --#ARGUMENTS {}
     --#SEVERITY CRITICAL
     --#TIMEINDEX 100
     --#STATE OPERATIONAL
::= 5511


hpevtReconfigResetFail TRAP-TYPE
     ENTERPRISE hpIpfE0Events
     VARIABLES { hpIpfEvtDetailStr }
     DESCRIPTION
        "System firmware is unable to complete the request to reset the cell for reconfiguration.  Typically, are required step has not been performed yet or a needed resource is unavailable."

     --#SUMMARY "System is unable to complete the Reset For Reconfiguration request."
     --#ARGUMENTS {}
     --#SEVERITY CRITICAL
     --#TIMEINDEX 100
     --#STATE OPERATIONAL
::= 5514


hpevtPdErrorReachableSet TRAP-TYPE
     ENTERPRISE hpIpfE0Events
     VARIABLES { hpIpfEvtDetailStr }
     DESCRIPTION
        "The cell was not able to reach all the other cells in its configured set through the fabric.  The data field contains the bitmask of actual cells that were reached."

     --#SUMMARY "The cell is not able to reach all requested cells through the fabric."
     --#ARGUMENTS {}
     --#SEVERITY CRITICAL
     --#TIMEINDEX 100
     --#STATE OPERATIONAL
::= 5515


hpevtIoBridgeDepthExceeded TRAP-TYPE
     ENTERPRISE hpIpfE0Events
     VARIABLES { hpIpfEvtDetailStr }
     DESCRIPTION
        "Firmware detected a PCI-to-PCI bridge that exceeds the maximum supported bridge depth.  Firmware will not configure I/O devices below the maximum bridge depth.  Such I/O devices will not be usable as console nor boot devices but might be usable by the O/S. 
Data Field: PCI function address of the bridge that exceeded the maximum depth limit. 
                   Bits 24..31: segment number 
                   Bits 16..23: bus number 
                   Bits 11..15: device number 
                   Bits  8..10: function number 
                   Bits  0..7: reserved (0)"

     --#SUMMARY "LBA has unexpected number of I/O Slots."
     --#ARGUMENTS {}
     --#SEVERITY WARNING
     --#TIMEINDEX 100
     --#STATE OPERATIONAL
::= 5518


hpevtEfiConsoleDriverError TRAP-TYPE
     ENTERPRISE hpIpfE0Events
     VARIABLES { hpIpfEvtDetailStr }
     DESCRIPTION
        "Debugging event, not for release.  This event is no longer used on Everest/xPeak systems but its event ID is still contained in the code base."

     --#SUMMARY "Console device failed to connect."
     --#ARGUMENTS {}
     --#SEVERITY CRITICAL
     --#TIMEINDEX 100
     --#STATE OPERATIONAL
::= 5521


hpevtMemTestCodeInPage0Corrupt TRAP-TYPE
     ENTERPRISE hpIpfE0Events
     VARIABLES { hpIpfEvtDetailStr }
     DESCRIPTION
        "This event is unused"

     --#SUMMARY "Copying memory test code failed."
     --#ARGUMENTS {}
     --#SEVERITY WARNING
     --#TIMEINDEX 100
     --#STATE OPERATIONAL
::= 5525


hpevtRemoteCellStateUnknown TRAP-TYPE
     ENTERPRISE hpIpfE0Events
     VARIABLES { hpIpfEvtDetailStr }
     DESCRIPTION
        "The reporting cell read an unknown state from a remote cell.  This chassis code will be emitted in pairs.  The first one indicating the cell number in the data field and the second code indicating the state read in the data field."

     --#SUMMARY "A remote cell is in an unknown state of PD rendezvous"
     --#ARGUMENTS {}
     --#SEVERITY CRITICAL
     --#TIMEINDEX 100
     --#STATE OPERATIONAL
::= 5527


hpevtPdMltplCoreCells TRAP-TYPE
     ENTERPRISE hpIpfE0Events
     VARIABLES { hpIpfEvtDetailStr }
     DESCRIPTION
        "The reporting Cell thinks that it should be the core cell but has discovered another cell in the same PD that thinks it should be the core cell.  This is a serious problem."

     --#SUMMARY "Multiple Core Cells have been discovered in the same PD"
     --#ARGUMENTS {}
     --#SEVERITY CRITICAL
     --#TIMEINDEX 100
     --#STATE OPERATIONAL
::= 5528


hpevtUtilSendCommandError TRAP-TYPE
     ENTERPRISE hpIpfE0Events
     VARIABLES { hpIpfEvtDetailStr }
     DESCRIPTION
        "The utilities system firmware component received an error response from the SINC in response to a command being sent.  The exact error is displayed in the data field.  Typically, this can occure when the SINC cannot talk to the MP."

     --#SUMMARY "The utilities component encountered an error when sending a command to the MP"
     --#ARGUMENTS {}
     --#SEVERITY CRITICAL
     --#TIMEINDEX 100
     --#STATE OPERATIONAL
::= 5529


hpevtUtilCellSlotError TRAP-TYPE
     ENTERPRISE hpIpfE0Events
     VARIABLES { hpIpfEvtDetailStr }
     DESCRIPTION
        "System Firmware issued the Retrieve Cell Slot State command to the Sync and got an error back.  See related chassis code or the specifics of the error."

     --#SUMMARY "Error received after issuing the Retrieve Cell Slot State command"
     --#ARGUMENTS {}
     --#SEVERITY WARNING
     --#TIMEINDEX 100
     --#STATE OPERATIONAL
::= 5530


hpevtMcCellRendezFailed TRAP-TYPE
     ENTERPRISE hpIpfE0Events
     VARIABLES { hpIpfEvtDetailStr }
     DESCRIPTION
        "This denotes the fact that all the cpus in the cell did not rendezvous."

     --#SUMMARY "This indicates that all the cpus in the cell did not rendezvous during the MCA."
     --#ARGUMENTS {}
     --#SEVERITY CRITICAL
     --#TIMEINDEX 100
     --#STATE OPERATIONAL
::= 5546


hpevtMcNoAccessToPd TRAP-TYPE
     ENTERPRISE hpIpfE0Events
     VARIABLES { hpIpfEvtDetailStr }
     DESCRIPTION
        "This chassis code indicates that thecell does not have any access to a PD."

     --#SUMMARY "This indicates that it does not have any access to the PD."
     --#ARGUMENTS {}
     --#SEVERITY CRITICAL
     --#TIMEINDEX 100
     --#STATE OPERATIONAL
::= 5547


hpevtMcLossOfLockstep TRAP-TYPE
     ENTERPRISE hpIpfE0Events
     VARIABLES { hpIpfEvtDetailStr }
     DESCRIPTION
        "This indicates the cell would not be able to join the other cells in the PD level rendezvous. The data portion represents the cell id of the cell that incurred the loss of lockstep."

     --#SUMMARY "This indicates the loss of lockstep during the MCA path."
     --#ARGUMENTS {}
     --#SEVERITY CRITICAL
     --#TIMEINDEX 100
     --#STATE OPERATIONAL
::= 5548


hpevtMcPdCellRendezFailed TRAP-TYPE
     ENTERPRISE hpIpfE0Events
     VARIABLES { hpIpfEvtDetailStr }
     DESCRIPTION
        "This inicates that some of the cells did not show up during the PD level rendezvous."

     --#SUMMARY "The PD level cell rendezvous failed."
     --#ARGUMENTS {}
     --#SEVERITY CRITICAL
     --#TIMEINDEX 100
     --#STATE OPERATIONAL
::= 5550


hpevtMcProcErrHalt TRAP-TYPE
     ENTERPRISE hpIpfE0Events
     VARIABLES { hpIpfEvtDetailStr }
     DESCRIPTION
        "This indicates that catastrophic errors have been found in the PIN block of the cell controller. The cell needs to be reset/ halt."

     --#SUMMARY "It stands for diagnosis of catastrophic errors in the PIN block of concorde."
     --#ARGUMENTS {}
     --#SEVERITY CRITICAL
     --#TIMEINDEX 100
     --#STATE OPERATIONAL
::= 5556


hpevtMcCellMonarchTimeout TRAP-TYPE
     ENTERPRISE hpIpfE0Events
     VARIABLES { hpIpfEvtDetailStr }
     DESCRIPTION
        "This means that the cell monach cpu has not completed the assigned task within the timeout and hence it will be deconfigured."

     --#SUMMARY "The cell monarch cpu has failed."
     --#ARGUMENTS {}
     --#SEVERITY CRITICAL
     --#TIMEINDEX 100
     --#STATE OPERATIONAL
::= 5557


hpevtMcPdCellMissedRendez TRAP-TYPE
     ENTERPRISE hpIpfE0Events
     VARIABLES { hpIpfEvtDetailStr }
     DESCRIPTION
        "This indicates that the cell is too late for the PD level rendezvous. And hence it will not join the other PD cells."

     --#SUMMARY "This indicates that the cell missed the rendezvous at the partition level."
     --#ARGUMENTS {}
     --#SEVERITY CRITICAL
     --#TIMEINDEX 100
     --#STATE OPERATIONAL
::= 5558


hpevtMcPdMonarchTimeout TRAP-TYPE
     ENTERPRISE hpIpfE0Events
     VARIABLES { hpIpfEvtDetailStr }
     DESCRIPTION
        "This indicates the state where the PD monarch was not able to complete the task within a certain time. It failed."

     --#SUMMARY "This means that the PD monarch timedout."
     --#ARGUMENTS {}
     --#SEVERITY CRITICAL
     --#TIMEINDEX 100
     --#STATE OPERATIONAL
::= 5559


hpevtRemoteSetViewRootError TRAP-TYPE
     ENTERPRISE hpIpfE0Events
     VARIABLES { hpIpfEvtDetailStr }
     DESCRIPTION
        "System firmware on the Core cell was unable to update a slave cell with the location of the root of the partition tree.  The CPU that was unable to be contacted is printed in the data field."

     --#SUMMARY "SetViewRoot on a remote cell failed."
     --#ARGUMENTS {}
     --#SEVERITY CRITICAL
     --#TIMEINDEX 100
     --#STATE OPERATIONAL
::= 5560


hpevtCsrTestFailure TRAP-TYPE
     ENTERPRISE hpIpfE0Events
     VARIABLES { hpIpfEvtDetailStr }
     DESCRIPTION
        "Read test on a CSR failed and the CSR contents were not updated.  This chassis code will be emitted in 3's, with the CSR Address, expected data, and actual data given."

     --#SUMMARY "Failed to update CSR contents"
     --#ARGUMENTS {}
     --#SEVERITY CRITICAL
     --#TIMEINDEX 100
     --#STATE OPERATIONAL
::= 5566


hpevtPdMemGetIcmInfoFailed TRAP-TYPE
     ENTERPRISE hpIpfE0Events
     VARIABLES { hpIpfEvtDetailStr }
     DESCRIPTION
        "This chassis code reports the failure in collecting the ICM parameters needed for the cell interleaving."

     --#SUMMARY "This indicates the failure in collecting the Complex profile info."
     --#ARGUMENTS {}
     --#SEVERITY CRITICAL
     --#TIMEINDEX 100
     --#STATE OPERATIONAL
::= 5567


hpevtPdMemGetCellInfoFailed TRAP-TYPE
     ENTERPRISE hpIpfE0Events
     VARIABLES { hpIpfEvtDetailStr }
     DESCRIPTION
        "This chassis code indicates that the cell intearleaving routine could not get the information on the cell memory."

     --#SUMMARY "This chassis code indicates the failure in collecting the cell info."
     --#ARGUMENTS {}
     --#SEVERITY CRITICAL
     --#TIMEINDEX 100
     --#STATE OPERATIONAL
::= 5568


hpevtPdMemUpdateCellGniFailed TRAP-TYPE
     ENTERPRISE hpIpfE0Events
     VARIABLES { hpIpfEvtDetailStr }
     DESCRIPTION
        "This chassis code is used to represent the failure in updating the GNI information of the cell with the CLM ( cell local memory) information obtained from the Complex Profile."

     --#SUMMARY "This indicates the failure in updating the  GNI info of the cell with CLM."
     --#ARGUMENTS {}
     --#SEVERITY CRITICAL
     --#TIMEINDEX 100
     --#STATE OPERATIONAL
::= 5569


hpevtPdMemAdjustMinZiFailed TRAP-TYPE
     ENTERPRISE hpIpfE0Events
     VARIABLES { hpIpfEvtDetailStr }
     DESCRIPTION
        "This represents the failure in adjusting the memory information with the minimum ZI requirements."

     --#SUMMARY "This indicates the failure in adjusting the mem info with Minimum ZI req."
     --#ARGUMENTS {}
     --#SEVERITY CRITICAL
     --#TIMEINDEX 100
     --#STATE OPERATIONAL
::= 5570


hpevtStableProfileXsumError TRAP-TYPE
     ENTERPRISE hpIpfE0Events
     VARIABLES { hpIpfEvtDetailStr }
     DESCRIPTION
        "Complex Profile A (Stable Profile) stored checksum does not match the calculated checksum.  The expected data and actual data are displayed in the 2 reporting event Ids."

     --#SUMMARY "Complex Profile A has a checksum error"
     --#ARGUMENTS {}
     --#SEVERITY CRITICAL
     --#TIMEINDEX 100
     --#STATE OPERATIONAL
::= 5572


hpevtDynamicProfileXsumError TRAP-TYPE
     ENTERPRISE hpIpfE0Events
     VARIABLES { hpIpfEvtDetailStr }
     DESCRIPTION
        "The Dynamic Complex Profile (Group B) stored checksum did not equal the calculated checksum.  The Expected Data and Actual date are displayed in successive chassis codes."

     --#SUMMARY "A Checksum error was encountered in the dynamic profile"
     --#ARGUMENTS {}
     --#SEVERITY WARNING
     --#TIMEINDEX 100
     --#STATE OPERATIONAL
::= 5573


hpevtPartitionProfileXsumError TRAP-TYPE
     ENTERPRISE hpIpfE0Events
     VARIABLES { hpIpfEvtDetailStr }
     DESCRIPTION
        "The stored value of the complex profile Group C does not match the calcuated value.  Expected data and actual data are stored in successive chassis codes."

     --#SUMMARY "A checksum error occurred on the Partitioin Profile."
     --#ARGUMENTS {}
     --#SEVERITY WARNING
     --#TIMEINDEX 100
     --#STATE OPERATIONAL
::= 5574


hpevtStableProfileSeqidInvalid TRAP-TYPE
     ENTERPRISE hpIpfE0Events
     VARIABLES { hpIpfEvtDetailStr }
     DESCRIPTION
        "The Complex Profile Group A sequence ID is invalid.  Booting cannot continue.  The actual data is in the chassis code data field."

     --#SUMMARY "The Stable Complex Profile Sequence Id is invalid"
     --#ARGUMENTS {}
     --#SEVERITY CRITICAL
     --#TIMEINDEX 100
     --#STATE OPERATIONAL
::= 5575


hpevtDynamicProfileSeqidInvalid TRAP-TYPE
     ENTERPRISE hpIpfE0Events
     VARIABLES { hpIpfEvtDetailStr }
     DESCRIPTION
        "The Dynamic Complex Profile (Group B) sequence ID is invalid.  The invalid Sequence ID is displayed in the data field."

     --#SUMMARY "The Dynamic Complex Profile Sequence ID is invalid"
     --#ARGUMENTS {}
     --#SEVERITY WARNING
     --#TIMEINDEX 100
     --#STATE OPERATIONAL
::= 5577


hpevtPartitionProfileSeqidInvalid TRAP-TYPE
     ENTERPRISE hpIpfE0Events
     VARIABLES { hpIpfEvtDetailStr }
     DESCRIPTION
        "The Group C Partition Complex Profile Sequence ID is invalid.  The value read is displayed in the data field."

     --#SUMMARY "The Partition Profile Sequence ID is invalid"
     --#ARGUMENTS {}
     --#SEVERITY CRITICAL
     --#TIMEINDEX 100
     --#STATE OPERATIONAL
::= 5578


hpevtEfiFwError TRAP-TYPE
     ENTERPRISE hpIpfE0Events
     VARIABLES { hpIpfEvtDetailStr }
     DESCRIPTION
        "An internal EFI firmware error was encountered.  This is usually caused by a bad parameter passed to a function, corrupt memory, corrupt malloc, corrupt firmware tree or something similar.  The data field contains the IP address of the function that encountered the error."

     --#SUMMARY "Internal Firmware Programming Error from the EFI portion of the firmware"
     --#ARGUMENTS {}
     --#SEVERITY CRITICAL
     --#TIMEINDEX 100
     --#STATE OPERATIONAL
::= 5579


hpevtCmplxProfilePdNumMismatch TRAP-TYPE
     ENTERPRISE hpIpfE0Events
     VARIABLES { hpIpfEvtDetailStr }
     DESCRIPTION
        "The Complex Profile Group A PD assignment for this cell does not match the PD or Partition number in Group C of the complex profile.  This is a fatal condition for the cell.  The PD number from group A will be emmitted first, followed by a subsequent code for the PD assigned in group C."

     --#SUMMARY "The PD numbers in Group A and Group C of the complex profile are inconsistant."
     --#ARGUMENTS {}
     --#SEVERITY CRITICAL
     --#TIMEINDEX 100
     --#STATE OPERATIONAL
::= 5580


hpevtCmplxProfilePdNumInvalid TRAP-TYPE
     ENTERPRISE hpIpfE0Events
     VARIABLES { hpIpfEvtDetailStr }
     DESCRIPTION
        "The Partition (PD) assigned to this cell in the complex profile group A and C is larger than the maximum allowed number of PDs as specified by Group A."

     --#SUMMARY "The PD number specified in the complex profile is out of range."
     --#ARGUMENTS {}
     --#SEVERITY CRITICAL
     --#TIMEINDEX 100
     --#STATE OPERATIONAL
::= 5581


hpevtXbcPortSm4Error TRAP-TYPE
     ENTERPRISE hpIpfE0Events
     VARIABLES { hpIpfEvtDetailStr }
     DESCRIPTION
        "Tried to obtain the port semaphore but GetPortSemaphore returned an ERROR.  Could be a failed write to the port semaphore crossbar CSR or another cell owned the semaphore.  Data field bits 32:63 contain the crossbar ID and bits 0:31 contain the port number for which the semaphore was being obtained."

     --#SUMMARY "Could not obtain the crossbar port semaphore"
     --#ARGUMENTS {}
     --#SEVERITY WARNING
     --#TIMEINDEX 100
     --#STATE OPERATIONAL
::= 5583


hpevtXbcPortSm4NotReleased TRAP-TYPE
     ENTERPRISE hpIpfE0Events
     VARIABLES { hpIpfEvtDetailStr }
     DESCRIPTION
        "Currently owned the port semaphore but could not release the semaphore.  Data field bits 32:63 contain the crossbar ID and bits 0:32 contain the port number."

     --#SUMMARY "Could not release the crossbar port semaphore."
     --#ARGUMENTS {}
     --#SEVERITY WARNING
     --#TIMEINDEX 100
     --#STATE OPERATIONAL
::= 5584


hpevtBootBmcTokenUploadFailure TRAP-TYPE
     ENTERPRISE hpIpfE0Events
     VARIABLES { hpIpfEvtDetailStr }
     DESCRIPTION
        "There was an error reading from the BMC token when attempting to write to SAL NVM.  This is a stop boot condition.
Data: Lower 32 bits, BMC Token Number.  Upper 32 bits, bmc return status."

     --#SUMMARY "BMC token upload failure"
     --#ARGUMENTS {}
     --#SEVERITY CRITICAL
     --#TIMEINDEX 100
     --#STATE OPERATIONAL
::= 5594


hpevtBootNvmTokenAccessFailure TRAP-TYPE
     ENTERPRISE hpIpfE0Events
     VARIABLES { hpIpfEvtDetailStr }
     DESCRIPTION
        "The read from SAL NVM has failed.  This is a stop boot condition.
Data:  The token number on which the read failed"

     --#SUMMARY "NVM token access failure"
     --#ARGUMENTS {}
     --#SEVERITY WARNING
     --#TIMEINDEX 100
     --#STATE OPERATIONAL
::= 5595


hpevtBootBmcTokenDownloadError TRAP-TYPE
     ENTERPRISE hpIpfE0Events
     VARIABLES { hpIpfEvtDetailStr }
     DESCRIPTION
        "There was an error when trying to write to a BMC Token.  This is a boot warning condition.
Data: lower 32 bits are BMC token number, upper 32 bits is the status return from the BMC."

     --#SUMMARY "BMC token download failure"
     --#ARGUMENTS {}
     --#SEVERITY WARNING
     --#TIMEINDEX 100
     --#STATE OPERATIONAL
::= 5596


hpevtBootErrorWritingFirstBootToken TRAP-TYPE
     ENTERPRISE hpIpfE0Events
     VARIABLES { hpIpfEvtDetailStr }
     DESCRIPTION
        "There has been an error writing the BMC_FIRST_BOOT token.  This is a stop boot condition."

     --#SUMMARY "Error Writing BMC first boot token"
     --#ARGUMENTS {}
     --#SEVERITY CRITICAL
     --#TIMEINDEX 100
     --#STATE OPERATIONAL
::= 5597


hpevtBootFruReadError TRAP-TYPE
     ENTERPRISE hpIpfE0Events
     VARIABLES { hpIpfEvtDetailStr }
     DESCRIPTION
        "The read of a FRU has failed. 
Data: Device ID of device that failed the FRU read."

     --#SUMMARY "Fru Id read error"
     --#ARGUMENTS {}
     --#SEVERITY WARNING
     --#TIMEINDEX 100
     --#STATE OPERATIONAL
::= 5598


hpevtBootFruXsumError TRAP-TYPE
     ENTERPRISE hpIpfE0Events
     VARIABLES { hpIpfEvtDetailStr }
     DESCRIPTION
        "The read of a FRU has failed the checksum test. 
Data: Device ID of device that failed the FRU read."

     --#SUMMARY "Fru Id checksum error"
     --#ARGUMENTS {}
     --#SEVERITY WARNING
     --#TIMEINDEX 100
     --#STATE OPERATIONAL
::= 5599


hpevtBootFruVersionError TRAP-TYPE
     ENTERPRISE hpIpfE0Events
     VARIABLES { hpIpfEvtDetailStr }
     DESCRIPTION
        "The read of a FRU has failed due to a version problem. 
Data: Device ID of device that failed the FRU read."

     --#SUMMARY "Fru Id version error"
     --#ARGUMENTS {}
     --#SEVERITY WARNING
     --#TIMEINDEX 100
     --#STATE OPERATIONAL
::= 5600


hpevtBootRomRevToFitRevWarning TRAP-TYPE
     ENTERPRISE hpIpfE0Events
     VARIABLES { hpIpfEvtDetailStr }
     DESCRIPTION
        "A ROM Rev and FIT Rev do not match. 
Data: Code for what didn't match: 0x1 = PAL_A, 0x2 = PAL_B, 0x4 = SAL_A, 0x8 = ACPI, 0xA = EFI"

     --#SUMMARY "Rom revision not equal to FIT revision"
     --#ARGUMENTS {}
     --#SEVERITY WARNING
     --#TIMEINDEX 100
     --#STATE OPERATIONAL
::= 5601


hpevtBootRomRevToRevBlockWarning TRAP-TYPE
     ENTERPRISE hpIpfE0Events
     VARIABLES { hpIpfEvtDetailStr }
     DESCRIPTION
        "A ROM Rev and Rev Block do not match. 
Data: Code for what didn't match: 0x3 = PAL, 0x5 = SAL_A, 0x7 = SAL_B, 0x9 = ACPI, 0xB = EFI, 0xC = BMC"

     --#SUMMARY "ROM revision not equal to Rev block"
     --#ARGUMENTS {}
     --#SEVERITY WARNING
     --#TIMEINDEX 100
     --#STATE OPERATIONAL
::= 5602


hpevtBootPrimaryFitBad TRAP-TYPE
     ENTERPRISE hpIpfE0Events
     VARIABLES { hpIpfEvtDetailStr }
     DESCRIPTION
        "The FIT is bad."

     --#SUMMARY "Primary Fit bad"
     --#ARGUMENTS {}
     --#SEVERITY WARNING
     --#TIMEINDEX 100
     --#STATE OPERATIONAL
::= 5603


hpevtBootSecondaryFitBad TRAP-TYPE
     ENTERPRISE hpIpfE0Events
     VARIABLES { hpIpfEvtDetailStr }
     DESCRIPTION
        "The FIT is bad."

     --#SUMMARY "Secondary Fit bad"
     --#ARGUMENTS {}
     --#SEVERITY WARNING
     --#TIMEINDEX 100
     --#STATE OPERATIONAL
::= 5604


hpevtBootPalARomWarning TRAP-TYPE
     ENTERPRISE hpIpfE0Events
     VARIABLES { hpIpfEvtDetailStr }
     DESCRIPTION
        "PAL_A_ROM has generated a warning."

     --#SUMMARY "PAL A execution rom warning"
     --#ARGUMENTS {}
     --#SEVERITY WARNING
     --#TIMEINDEX 100
     --#STATE OPERATIONAL
::= 5605


hpevtBootPalBRomWarning TRAP-TYPE
     ENTERPRISE hpIpfE0Events
     VARIABLES { hpIpfEvtDetailStr }
     DESCRIPTION
        "PAL_B_ROM has generated a warning."

     --#SUMMARY "PAL B execution rom warning"
     --#ARGUMENTS {}
     --#SEVERITY WARNING
     --#TIMEINDEX 100
     --#STATE OPERATIONAL
::= 5606


hpevtErrorUpdatingGroupBProfile TRAP-TYPE
     ENTERPRISE hpIpfE0Events
     VARIABLES { hpIpfEvtDetailStr }
     DESCRIPTION
        "Firmware tried to default the Dynamic (Group B) complex profile and encountered an error."

     --#SUMMARY "An error was encountered when firmware tried to update the Group B Profile"
     --#ARGUMENTS {}
     --#SEVERITY CRITICAL
     --#TIMEINDEX 100
     --#STATE OPERATIONAL
::= 5607


hpevtIoPciPerr TRAP-TYPE
     ENTERPRISE hpIpfE0Events
     VARIABLES { hpIpfEvtDetailStr }
     DESCRIPTION
        "An I/O device (or host bridge) detected a bus parity error. 
An I/O device (or host bridge) mastered a bus transaction and received a parity error response from the target. 
Data Field: Physical location of the I/O device (or host bridge)."

     --#SUMMARY "PCI parity error detected."
     --#ARGUMENTS {}
     --#SEVERITY WARNING
     --#TIMEINDEX 100
     --#STATE OPERATIONAL
::= 5617


hpevtIoPciSerr TRAP-TYPE
     ENTERPRISE hpIpfE0Events
     VARIABLES { hpIpfEvtDetailStr }
     DESCRIPTION
        "An I/O device (or host bridge) detected an internal error. 
An I/O device (or host bridge) detected a bus error. 
Data Field: Physical location of the I/O device (or host bridge)."

     --#SUMMARY "PCI system error detected"
     --#ARGUMENTS {}
     --#SEVERITY WARNING
     --#TIMEINDEX 100
     --#STATE OPERATIONAL
::= 5618


hpevtIoCheckLbaDeconfigErr TRAP-TYPE
     ENTERPRISE hpIpfE0Events
     VARIABLES { hpIpfEvtDetailStr }
     DESCRIPTION
        "Firmware has deconfigured an I/O host bridge due to an error (see earlier error event).  Firmware will display the following EFI warning message, 'Failed I/O slot(s) deconfigured.' 
Data Field: Physical location of the deconfigured I/O host bridge."

     --#SUMMARY "I/O host bridge is deconfigured"
     --#ARGUMENTS {}
     --#SEVERITY WARNING
     --#TIMEINDEX 100
     --#STATE OPERATIONAL
::= 5619


hpevtErrorUpdatingGroupCProfile TRAP-TYPE
     ENTERPRISE hpIpfE0Events
     VARIABLES { hpIpfEvtDetailStr }
     DESCRIPTION
        "Firmware tried to default the Partition (Group C) complex profile and encountered an error."

     --#SUMMARY "Firmware was unable to publish the Partition Profile"
     --#ARGUMENTS {}
     --#SEVERITY CRITICAL
     --#TIMEINDEX 100
     --#STATE OPERATIONAL
::= 5621


hpevtCellNotInAPd TRAP-TYPE
     ENTERPRISE hpIpfE0Events
     VARIABLES { hpIpfEvtDetailStr }
     DESCRIPTION
        "The Reporting Cell is not configured to be in a PD, according to Complex Profile Group A."

     --#SUMMARY "The reporting cell is not configured to be in a PD."
     --#ARGUMENTS {}
     --#SEVERITY CRITICAL
     --#TIMEINDEX 100
     --#STATE OPERATIONAL
::= 5622


hpevtMemDimmThermalLoadOrderWarn TRAP-TYPE
     ENTERPRISE hpIpfE0Events
     VARIABLES { hpIpfEvtDetailStr }
     DESCRIPTION
        "DIMMs are not loaded on the extender in a thermally optimal way.  Boot is still possible, but the DIMM arrangement should be changed to the loading order recommended in the users manual.  The data field indicates the number of the extender with incorrectly loaded DIMMs."

     --#SUMMARY "DIMM thermal loading order warning"
     --#ARGUMENTS {}
     --#SEVERITY WARNING
     --#TIMEINDEX 100
     --#STATE OPERATIONAL
::= 5623


hpevtCellMajorityNotPresent TRAP-TYPE
     ENTERPRISE hpIpfE0Events
     VARIABLES { hpIpfEvtDetailStr }
     DESCRIPTION
        "Not enough cells made the Rendezvous for boot to continue.  The rules are listed in the cause action section."

     --#SUMMARY "The PD cannot boot, a majority of cells did not arrive at Rendezvous"
     --#ARGUMENTS {}
     --#SEVERITY CRITICAL
     --#TIMEINDEX 100
     --#STATE OPERATIONAL
::= 5626


hpevtInitRendezvousSlavesFail TRAP-TYPE
     ENTERPRISE hpIpfE0Events
     VARIABLES { hpIpfEvtDetailStr }
     DESCRIPTION
        "SFW's INIT handler failed to rendezvous the processors."

     --#SUMMARY "INIT: Monarch failed in slave rendezvous"
     --#ARGUMENTS {}
     --#SEVERITY WARNING
     --#TIMEINDEX 100
     --#STATE OPERATIONAL
::= 5638


hpevtMcIoClearFail TRAP-TYPE
     ENTERPRISE hpIpfE0Events
     VARIABLES { hpIpfEvtDetailStr }
     DESCRIPTION
        "SFW's Machine Check Handler was unable to log or clear I/O error registers."

     --#SUMMARY "MC: I/O error log/clear error"
     --#ARGUMENTS {}
     --#SEVERITY WARNING
     --#TIMEINDEX 100
     --#STATE OPERATIONAL
::= 5646


hpevtMcPalCantEscalateToBerr TRAP-TYPE
     ENTERPRISE hpIpfE0Events
     VARIABLES { hpIpfEvtDetailStr }
     DESCRIPTION
        "Cannot escalate an MCA to BERR"

     --#SUMMARY "MC: MCA to BERR escalation not supported by PAL"
     --#ARGUMENTS {}
     --#SEVERITY WARNING
     --#TIMEINDEX 100
     --#STATE OPERATIONAL
::= 5655


hpevtMcPalCantEscalateToBinit TRAP-TYPE
     ENTERPRISE hpIpfE0Events
     VARIABLES { hpIpfEvtDetailStr }
     DESCRIPTION
        "Cannot escalate an MCA to BINIT."

     --#SUMMARY "MC:  MCA to BINIT escalation not supported by PAL"
     --#ARGUMENTS {}
     --#SEVERITY WARNING
     --#TIMEINDEX 100
     --#STATE OPERATIONAL
::= 5656


hpevtMcPalGetFeatFail TRAP-TYPE
     ENTERPRISE hpIpfE0Events
     VARIABLES { hpIpfEvtDetailStr }
     DESCRIPTION
        "SFW failed to get the feature set from PAL."

     --#SUMMARY "MC: Get PAL features failed"
     --#ARGUMENTS {}
     --#SEVERITY WARNING
     --#TIMEINDEX 100
     --#STATE OPERATIONAL
::= 5657


hpevtMcPalRendFail TRAP-TYPE
     ENTERPRISE hpIpfE0Events
     VARIABLES { hpIpfEvtDetailStr }
     DESCRIPTION
        "PAL Failed to rendezvous the processors during a MCA."

     --#SUMMARY "MC: Previous PAL rendezvous failed; rebooting"
     --#ARGUMENTS {}
     --#SEVERITY WARNING
     --#TIMEINDEX 100
     --#STATE OPERATIONAL
::= 5658


hpevtMcPalSetFeatFail TRAP-TYPE
     ENTERPRISE hpIpfE0Events
     VARIABLES { hpIpfEvtDetailStr }
     DESCRIPTION
        "SFW failed to get the feature set from PAL."

     --#SUMMARY "MC: Set PAL features failed"
     --#ARGUMENTS {}
     --#SEVERITY WARNING
     --#TIMEINDEX 100
     --#STATE OPERATIONAL
::= 5659


hpevtMcRendezvousSlavesFail TRAP-TYPE
     ENTERPRISE hpIpfE0Events
     VARIABLES { hpIpfEvtDetailStr }
     DESCRIPTION
        "SFW's MCA Handler has failed to rendezvous all the slaves 
Data: Return from the rendezvous call."

     --#SUMMARY "MC: Monarch failed in slave rendezvous"
     --#ARGUMENTS {}
     --#SEVERITY WARNING
     --#TIMEINDEX 100
     --#STATE OPERATIONAL
::= 5677


hpevtMcRendezBadVectRange TRAP-TYPE
     ENTERPRISE hpIpfE0Events
     VARIABLES { hpIpfEvtDetailStr }
     DESCRIPTION
        "A bad rendezvous vector has been registered."

     --#SUMMARY "MC_RENDEZVOUS: Rendezvous vector out of range"
     --#ARGUMENTS {}
     --#SEVERITY WARNING
     --#TIMEINDEX 100
     --#STATE OPERATIONAL
::= 5679


hpevtMcRendezNoMonarch TRAP-TYPE
     ENTERPRISE hpIpfE0Events
     VARIABLES { hpIpfEvtDetailStr }
     DESCRIPTION
        "No Machine Check Monarch exists, exiting MC Rendezvous."

     --#SUMMARY "MC_RENDEZVOUS: No MC monarch"
     --#ARGUMENTS {}
     --#SEVERITY WARNING
     --#TIMEINDEX 100
     --#STATE OPERATIONAL
::= 5682


hpevtMcRendezNoWakeup TRAP-TYPE
     ENTERPRISE hpIpfE0Events
     VARIABLES { hpIpfEvtDetailStr }
     DESCRIPTION
        "The OS has not registered a wake-up mechanism for rendezvous."

     --#SUMMARY "MC_RENDEZVOUS: No wakeup registered"
     --#ARGUMENTS {}
     --#SEVERITY WARNING
     --#TIMEINDEX 100
     --#STATE OPERATIONAL
::= 5683


hpevtMcRendezPalCantEscalate TRAP-TYPE
     ENTERPRISE hpIpfE0Events
     VARIABLES { hpIpfEvtDetailStr }
     DESCRIPTION
        "PAL call failed to set the BINIT escalation bit"

     --#SUMMARY "MC_RENDEZVOUS: MCA escalation not supported by PAL"
     --#ARGUMENTS {}
     --#SEVERITY WARNING
     --#TIMEINDEX 100
     --#STATE OPERATIONAL
::= 5684


hpevtMcRendezPalGetFeatFail TRAP-TYPE
     ENTERPRISE hpIpfE0Events
     VARIABLES { hpIpfEvtDetailStr }
     DESCRIPTION
        "The PAL call PAL_GET_FEATURES has failed."

     --#SUMMARY "MC_RENDEZVOUS: Get PAL features failed"
     --#ARGUMENTS {}
     --#SEVERITY WARNING
     --#TIMEINDEX 100
     --#STATE OPERATIONAL
::= 5685


hpevtMcRendezPalSetFeatFail TRAP-TYPE
     ENTERPRISE hpIpfE0Events
     VARIABLES { hpIpfEvtDetailStr }
     DESCRIPTION
        "The PAL call PAL_SET_FEATURES has failed."

     --#SUMMARY "MC_RENDEZVOUS: Set PAL features failed"
     --#ARGUMENTS {}
     --#SEVERITY WARNING
     --#TIMEINDEX 100
     --#STATE OPERATIONAL
::= 5686


hpevtSalAbiFwError TRAP-TYPE
     ENTERPRISE hpIpfE0Events
     VARIABLES { hpIpfEvtDetailStr }
     DESCRIPTION
        "An internal SAL_ABI firmware error was encountered.  This is usually caused by a bad parameter passed to a function, corrupt memory, corrupt malloc, corrupt firmware tree or something similar.  The data field contains the IP address of the function that encountered the error."

     --#SUMMARY "Internal Firmware Programming Error from the EFI portion of the firmware"
     --#ARGUMENTS {}
     --#SEVERITY CRITICAL
     --#TIMEINDEX 100
     --#STATE OPERATIONAL
::= 5692


hpevtMemExtLoadOrdErr TRAP-TYPE
     ENTERPRISE hpIpfE0Events
     VARIABLES { hpIpfEvtDetailStr }
     DESCRIPTION
        "The Memory extenders have not been loaded in the correct order."

     --#SUMMARY "memory extender loading order error"
     --#ARGUMENTS {}
     --#SEVERITY CRITICAL
     --#TIMEINDEX 100
     --#STATE OPERATIONAL
::= 5696


hpevtEfiEsiTableLengthErr TRAP-TYPE
     ENTERPRISE hpIpfE0Events
     VARIABLES { hpIpfEvtDetailStr }
     DESCRIPTION
        "The length field within the ESI (Extensible SAL Interface) table does not agree with the product of the entry_count field and the size of each entry. 
Data Field:   computed value of the length based on entry_count and size of the entries."

     --#SUMMARY "Inconsistency in the length of the ESI table"
     --#ARGUMENTS {}
     --#SEVERITY CRITICAL
     --#TIMEINDEX 100
     --#STATE OPERATIONAL
::= 5698


hpevtEfiEsiTableChecksumErr TRAP-TYPE
     ENTERPRISE hpIpfE0Events
     VARIABLES { hpIpfEvtDetailStr }
     DESCRIPTION
        "The computed checksum for the ESI (Extensible SAL Interface) table is not zero as expected.  EFI is halting. 
Data Field:  the computed checksum."

     --#SUMMARY "The computed checksum for ESI Table incorrect."
     --#ARGUMENTS {}
     --#SEVERITY CRITICAL
     --#TIMEINDEX 100
     --#STATE OPERATIONAL
::= 5700


hpevtEfiEsiTableUnsupportedEntryType TRAP-TYPE
     ENTERPRISE hpIpfE0Events
     VARIABLES { hpIpfEvtDetailStr }
     DESCRIPTION
        "EFI found an unsupported entry type within the ESI (Extensible SAL Interface) Table. 
Data Field:  unknown type."

     --#SUMMARY "ESI Table contains an unsupported entry type."
     --#ARGUMENTS {}
     --#SEVERITY WARNING
     --#TIMEINDEX 100
     --#STATE OPERATIONAL
::= 5701


hpevtEfiGuidTooLarge TRAP-TYPE
     ENTERPRISE hpIpfE0Events
     VARIABLES { hpIpfEvtDetailStr }
     DESCRIPTION
        "EFI was attempting to output a GUID in the EFI_GUID_HALF1 and EFI_GUID_HALF2 events which was larger than 128 bits.  The data field contains the actual length of the GUID in bytes."

     --#SUMMARY "A GUID was larger than the expected 128 bits."
     --#ARGUMENTS {}
     --#SEVERITY WARNING
     --#TIMEINDEX 100
     --#STATE OPERATIONAL
::= 5704


hpevtEfiHalt TRAP-TYPE
     ENTERPRISE hpIpfE0Events
     VARIABLES { hpIpfEvtDetailStr }
     DESCRIPTION
        "EFI is halting.  Look for the cause of the halt in preceding events. 
Data Field:   the 'halt' (0x0F) major change in system state code."

     --#SUMMARY "EFI is halting"
     --#ARGUMENTS {}
     --#SEVERITY CRITICAL
     --#TIMEINDEX 100
     --#STATE OPERATIONAL
::= 5708


hpevtMemChipspareNotSupported TRAP-TYPE
     ENTERPRISE hpIpfE0Events
     VARIABLES { hpIpfEvtDetailStr }
     DESCRIPTION
        "This code will be sent when FW detects a rank installed in the system that doesn't support chipspare.  The data field is used to indicate the rank that the x8 DIMMs are installed.  It is in the format 0x00000000XDXCXBXA or 0x00000000YBYAXBXA where X and Y are the number of the rank."

     --#SUMMARY "chipspare not supported on quad"
     --#ARGUMENTS {}
     --#SEVERITY WARNING
     --#TIMEINDEX 100
     --#STATE OPERATIONAL
::= 5711


hpevtEfiAssertError TRAP-TYPE
     ENTERPRISE hpIpfE0Events
     VARIABLES { hpIpfEvtDetailStr }
     DESCRIPTION
        "EFI has detected an internal error.  The actual error is unspecified by this event.  Examine previous events and console output for possible explanations."

     --#SUMMARY "EFI internal error detected resulting in execution of ASSERT macro"
     --#ARGUMENTS {}
     --#SEVERITY WARNING
     --#TIMEINDEX 100
     --#STATE OPERATIONAL
::= 5712


hpevtEfiEfiBreakpoint TRAP-TYPE
     ENTERPRISE hpIpfE0Events
     VARIABLES { hpIpfEvtDetailStr }
     DESCRIPTION
        "EFI has executed the 'break' shell command.  EFI is halting.  The 'break' command is currently implemented as an infinite loop to halt EFI."

     --#SUMMARY "EFI has executed the "break" shell command."
     --#ARGUMENTS {}
     --#SEVERITY CRITICAL
     --#TIMEINDEX 100
     --#STATE OPERATIONAL
::= 5713


hpevtEfiHcdHostHung TRAP-TYPE
     ENTERPRISE hpIpfE0Events
     VARIABLES { hpIpfEvtDetailStr }
     DESCRIPTION
        "The EFI USB interrupt service has detected the host controller is hung.  EFI is halting."

     --#SUMMARY "EFI USB HCD interrupt service has detected the host controller is hung"
     --#ARGUMENTS {}
     --#SEVERITY CRITICAL
     --#TIMEINDEX 100
     --#STATE OPERATIONAL
::= 5714


hpevtEfiSalHandoffVerMismatch TRAP-TYPE
     ENTERPRISE hpIpfE0Events
     VARIABLES { hpIpfEvtDetailStr }
     DESCRIPTION
        "The EFI/SAL handoff structure's version does not match EFI expectations.  EFI is halting.  Look for EFI_SAL_HANDOFF_VER_EXPECTED to provide EFI's expected value. 
Data Field:   Actual value of the version in the structure."

     --#SUMMARY "The EFI/SAL handoff structure's version does not match EFI expectations"
     --#ARGUMENTS {}
     --#SEVERITY CRITICAL
     --#TIMEINDEX 100
     --#STATE OPERATIONAL
::= 5715


hpevtEfiSalRtcServiceNotInit TRAP-TYPE
     ENTERPRISE hpIpfE0Events
     VARIABLES { hpIpfEvtDetailStr }
     DESCRIPTION
        "EFI is unable to obtain access to all the RTC (Real Time Clock) SAL services.  This means that EFI is unable to fully interact with the RTC.  EFI is halting. 
Data Field:  Return status from internal EFI function."

     --#SUMMARY "Unable to obtain access to all RTC SAL services"
     --#ARGUMENTS {}
     --#SEVERITY CRITICAL
     --#TIMEINDEX 100
     --#STATE OPERATIONAL
::= 5717


hpevtEfiSalTimerServiceNotInit TRAP-TYPE
     ENTERPRISE hpIpfE0Events
     VARIABLES { hpIpfEvtDetailStr }
     DESCRIPTION
        "EFI is unable to obtain access to all the  SAL timer services.  This means that EFI is unable to fully interact with the timer.   EFI is halting. 
Data Field:  Return status from internal EFI function."

     --#SUMMARY "Unable to obtain access to all SAL timer services"
     --#ARGUMENTS {}
     --#SEVERITY CRITICAL
     --#TIMEINDEX 100
     --#STATE OPERATIONAL
::= 5718


hpevtEfiSalStarttimerServiceNotInit TRAP-TYPE
     ENTERPRISE hpIpfE0Events
     VARIABLES { hpIpfEvtDetailStr }
     DESCRIPTION
        "EFI is unable to start the periodic timer.  This timer interrupts EFI periodically to process time sensitive events.   EFI is halting. 
Data Field:  Return status for internal EFI function."

     --#SUMMARY "EFI unable to start the periodic timer"
     --#ARGUMENTS {}
     --#SEVERITY CRITICAL
     --#TIMEINDEX 100
     --#STATE OPERATIONAL
::= 5719


hpevtEfiNoIoPortSpaceRegionFound TRAP-TYPE
     ENTERPRISE hpIpfE0Events
     VARIABLES { hpIpfEvtDetailStr }
     DESCRIPTION
        "EFI did not find an I/O port space region in the MDT.  EFI is halting."

     --#SUMMARY "No I/O port space region found in the MDT"
     --#ARGUMENTS {}
     --#SEVERITY CRITICAL
     --#TIMEINDEX 100
     --#STATE OPERATIONAL
::= 5720


hpevtEfiBreakpoint TRAP-TYPE
     ENTERPRISE hpIpfE0Events
     VARIABLES { hpIpfEvtDetailStr }
     DESCRIPTION
        "EFI reached an unimplemented section of code.  EFI is halting. 
Data Field: Unique identifier indicating the location reached within the code."

     --#SUMMARY "EFI reached an unimplemented section of code"
     --#ARGUMENTS {}
     --#SEVERITY CRITICAL
     --#TIMEINDEX 100
     --#STATE OPERATIONAL
::= 5721


hpevtEfiSpeedyBootTokenNotRead TRAP-TYPE
     ENTERPRISE hpIpfE0Events
     VARIABLES { hpIpfEvtDetailStr }
     DESCRIPTION
        "EFI was unable to read the current speedy boot settings.  The speedy boot settings are stored  within the BMC.  EFI will use a default value of 0 and continue booting.  The speedy boot functionality is also accessed via the boot test EFI shell command and via the OS.  These other accesses will likely fail. 
Data Field:  Return status from internal EFI function.."

     --#SUMMARY "EFI unable to read current speedy boot settings"
     --#ARGUMENTS {}
     --#SEVERITY WARNING
     --#TIMEINDEX 100
     --#STATE OPERATIONAL
::= 5722


hpevtEfiSalCallbackAttempted TRAP-TYPE
     ENTERPRISE hpIpfE0Events
     VARIABLES { hpIpfEvtDetailStr }
     DESCRIPTION
        "A SAL Callback was attempted.  This is not permitted.  EFI is halting. 
Data Field:   index of the function that was being called."

     --#SUMMARY "Unpermitted SAL callback attempted"
     --#ARGUMENTS {}
     --#SEVERITY CRITICAL
     --#TIMEINDEX 100
     --#STATE OPERATIONAL
::= 5723


hpevtEfiSalFreqBaseUnknown TRAP-TYPE
     ENTERPRISE hpIpfE0Events
     VARIABLES { hpIpfEvtDetailStr }
     DESCRIPTION
        "While attempting to calibrate the EFI stall timer, system firmware is unable to determine the frequency of the CPU interval timer.  System firmware will assume 800 MHz for the purpose of the stall timer calibration and continue boot. 
Data Field:   error status code (should be 0xFFFFFFFD)."

     --#SUMMARY "EFI unable to determine frequency base of the CPU interval timer"
     --#ARGUMENTS {}
     --#SEVERITY WARNING
     --#TIMEINDEX 100
     --#STATE OPERATIONAL
::= 5724


hpevtEfiSysEventAlreadyInit TRAP-TYPE
     ENTERPRISE hpIpfE0Events
     VARIABLES { hpIpfEvtDetailStr }
     DESCRIPTION
        "The EFI system events have already been initialized.  This is unexpected.  EFI is continuing. 
Data Field:  the current value of the system event entry point."

     --#SUMMARY "EFI system events already initialized"
     --#ARGUMENTS {}
     --#SEVERITY WARNING
     --#TIMEINDEX 100
     --#STATE OPERATIONAL
::= 5725


hpevtEfiSysEventCreateEventFail TRAP-TYPE
     ENTERPRISE hpIpfE0Events
     VARIABLES { hpIpfEvtDetailStr }
     DESCRIPTION
        "EFI was unable to create an internal virtualization event while initializing EFI's System Events (IPMI events).  This internal event is not an IPMI event; rather it serves as a trigger for EFI to virtualize the System Event facility when going virtual.  EFI will likely halt. 
Data Field:  return status from internal EFI function."

     --#SUMMARY "Unable to create internal virtualization event while initializing IPMI events"
     --#ARGUMENTS {}
     --#SEVERITY WARNING
     --#TIMEINDEX 100
     --#STATE OPERATIONAL
::= 5726


hpevtFpgaNodeInitError TRAP-TYPE
     ENTERPRISE hpIpfE0Events
     VARIABLES { hpIpfEvtDetailStr }
     DESCRIPTION
        "An error was detected while initializing the FPGA node and services asociated with the PDH."

     --#SUMMARY "There was an error creating or initializing the FPGA node in firmware"
     --#ARGUMENTS {}
     --#SEVERITY CRITICAL
     --#TIMEINDEX 100
     --#STATE OPERATIONAL
::= 5728


hpevtIoconfigNodeInitError TRAP-TYPE
     ENTERPRISE hpIpfE0Events
     VARIABLES { hpIpfEvtDetailStr }
     DESCRIPTION
        "Firmware encountered an error when creating the ioconfig node as a child of the pdh node."

     --#SUMMARY "Error creating the pdh ioconfig node or attaching the service to it."
     --#ARGUMENTS {}
     --#SEVERITY CRITICAL
     --#TIMEINDEX 100
     --#STATE OPERATIONAL
::= 5729


hpevtDillonPdhNodeInitError TRAP-TYPE
     ENTERPRISE hpIpfE0Events
     VARIABLES { hpIpfEvtDetailStr }
     DESCRIPTION
        "System firmware was unable to correctly set up the pdh arbiter node as a child of the pdh node, or was unable to locate and attach the pdh arbiter service to the node.  The status is returned in the data field."

     --#SUMMARY "Error ecnountered setting up the dillon_pdh node or service."
     --#ARGUMENTS {}
     --#SEVERITY CRITICAL
     --#TIMEINDEX 100
     --#STATE OPERATIONAL
::= 5730


hpevtPdhPropertyError TRAP-TYPE
     ENTERPRISE hpIpfE0Events
     VARIABLES { hpIpfEvtDetailStr }
     DESCRIPTION
        "The PDH service was unable to either get or set the property specified in the data field as an ascii message."

     --#SUMMARY "The PDH component encountered an error dealing with a property on a node."
     --#ARGUMENTS {}
     --#SEVERITY CRITICAL
     --#TIMEINDEX 100
     --#STATE OPERATIONAL
::= 5731


hpevtPdhAcpihwNodeError TRAP-TYPE
     ENTERPRISE hpIpfE0Events
     VARIABLES { hpIpfEvtDetailStr }
     DESCRIPTION
        "PDH encountered an error creating the ACPI Hardware Node in the device tree or installing its properties."

     --#SUMMARY "Error creating the acpi_hw node."
     --#ARGUMENTS {}
     --#SEVERITY CRITICAL
     --#TIMEINDEX 100
     --#STATE OPERATIONAL
::= 5732


hpevtPdhIpmiNodeError TRAP-TYPE
     ENTERPRISE hpIpfE0Events
     VARIABLES { hpIpfEvtDetailStr }
     DESCRIPTION
        "The PDH service encountered an error while creating the ipmi node or adding properties to it.  The status is in the data field."

     --#SUMMARY "Error encountered creating or initializing the ipmi node"
     --#ARGUMENTS {}
     --#SEVERITY CRITICAL
     --#TIMEINDEX 100
     --#STATE OPERATIONAL
::= 5733


hpevtBootCpusNotCompatible TRAP-TYPE
     ENTERPRISE hpIpfE0Events
     VARIABLES { hpIpfEvtDetailStr }
     DESCRIPTION
        "Installed processors are not of compatible models or families"

     --#SUMMARY "some processors not compatible"
     --#ARGUMENTS {}
     --#SEVERITY CRITICAL
     --#TIMEINDEX 100
     --#STATE OPERATIONAL
::= 5734


hpevtBootCacheSizesInconsistant TRAP-TYPE
     ENTERPRISE hpIpfE0Events
     VARIABLES { hpIpfEvtDetailStr }
     DESCRIPTION
        "Processors with different cache sizes are installed"

     --#SUMMARY "caches sizes are inconsistent"
     --#ARGUMENTS {}
     --#SEVERITY CRITICAL
     --#TIMEINDEX 100
     --#STATE OPERATIONAL
::= 5735


hpevtBootSelectingNewMonarch TRAP-TYPE
     ENTERPRISE hpIpfE0Events
     VARIABLES { hpIpfEvtDetailStr }
     DESCRIPTION
        "SFW is selecting a new monarch processor due to compatibility problems."

     --#SUMMARY "selecting new monarch"
     --#ARGUMENTS {}
     --#SEVERITY WARNING
     --#TIMEINDEX 100
     --#STATE OPERATIONAL
::= 5737


hpevtBootMonSelSteppingsNoEqual TRAP-TYPE
     ENTERPRISE hpIpfE0Events
     VARIABLES { hpIpfEvtDetailStr }
     DESCRIPTION
        "The monarch stepping is not equal to the lowest installed CPU stepping."

     --#SUMMARY "monarch not lowest stepping"
     --#ARGUMENTS {}
     --#SEVERITY WARNING
     --#TIMEINDEX 100
     --#STATE OPERATIONAL
::= 5738


hpevtBootCpuOverClocked TRAP-TYPE
     ENTERPRISE hpIpfE0Events
     VARIABLES { hpIpfEvtDetailStr }
     DESCRIPTION
        "A CPU's FSB frequency is overclocked. 
Data: Local CPU Number."

     --#SUMMARY "processors are over clocked"
     --#ARGUMENTS {}
     --#SEVERITY WARNING
     --#TIMEINDEX 100
     --#STATE OPERATIONAL
::= 5740


hpevtBootCpuInfoRomAccessError TRAP-TYPE
     ENTERPRISE hpIpfE0Events
     VARIABLES { hpIpfEvtDetailStr }
     DESCRIPTION
        "There was an error reading the info ROM area of the CPU.
Data: Local CPU Number"

     --#SUMMARY "cpu access error on processor info area"
     --#ARGUMENTS {}
     --#SEVERITY WARNING
     --#TIMEINDEX 100
     --#STATE OPERATIONAL
::= 5741


hpevtBootPalANotExecuted TRAP-TYPE
     ENTERPRISE hpIpfE0Events
     VARIABLES { hpIpfEvtDetailStr }
     DESCRIPTION
        "PAL_A has not been executed and control has been transferred back to SAL_B."

     --#SUMMARY "PAL A was not executed - HALT"
     --#ARGUMENTS {}
     --#SEVERITY CRITICAL
     --#TIMEINDEX 100
     --#STATE OPERATIONAL
::= 5742


hpevtBootPalBNotExecuted TRAP-TYPE
     ENTERPRISE hpIpfE0Events
     VARIABLES { hpIpfEvtDetailStr }
     DESCRIPTION
        "PAL_B has not been executed and control has been transferred back to SAL_B."

     --#SUMMARY "PAL B was not executed - HALT"
     --#ARGUMENTS {}
     --#SEVERITY CRITICAL
     --#TIMEINDEX 100
     --#STATE OPERATIONAL
::= 5743


hpevtBootProtoTypeCpuInstalled TRAP-TYPE
     ENTERPRISE hpIpfE0Events
     VARIABLES { hpIpfEvtDetailStr }
     DESCRIPTION
        "Data: Lower 32 bits have Local CPU Number"

     --#SUMMARY "Prototype CPU installed"
     --#ARGUMENTS {}
     --#SEVERITY WARNING
     --#TIMEINDEX 100
     --#STATE OPERATIONAL
::= 5744


hpevtBootFinalRendezWatchdogFail TRAP-TYPE
     ENTERPRISE hpIpfE0Events
     VARIABLES { hpIpfEvtDetailStr }
     DESCRIPTION
        "Data: Monarch's Local CPU Number"

     --#SUMMARY "final boot rendezvous monarch watchdog timeout"
     --#ARGUMENTS {}
     --#SEVERITY WARNING
     --#TIMEINDEX 100
     --#STATE OPERATIONAL
::= 5745


hpevtCpuSupplementalTestFailed TRAP-TYPE
     ENTERPRISE hpIpfE0Events
     VARIABLES { hpIpfEvtDetailStr }
     DESCRIPTION
        "Supplemental tests have been run on the cpus in the node and an error was encountered.  If this event id is only emmitted once, then the cpu detected that it failed on its own and the offending CPU id is in the data field.  If the event is emmitted three times, then the monarch CPU on the cell detected the error and the offending CPU id, expected data and actual data are reported in the data field of the three events."

     --#SUMMARY "Supplemental cpu tests generated an unexpected result"
     --#ARGUMENTS {}
     --#SEVERITY CRITICAL
     --#TIMEINDEX 100
     --#STATE OPERATIONAL
::= 5746


hpevtFabricReadMbeError TRAP-TYPE
     ENTERPRISE hpIpfE0Events
     VARIABLES { hpIpfEvtDetailStr }
     DESCRIPTION
        "While reading a XBC CSR, a multi-bit error was found."

     --#SUMMARY "A multi-bit error was found while reading a XBC CSR"
     --#ARGUMENTS {}
     --#SEVERITY WARNING
     --#TIMEINDEX 100
     --#STATE OPERATIONAL
::= 5747


hpevtFabricUnexpectedStatus TRAP-TYPE
     ENTERPRISE hpIpfE0Events
     VARIABLES { hpIpfEvtDetailStr }
     DESCRIPTION
        "The return value from a function was an unknown value.  Data field is the unknown status that was returned."

     --#SUMMARY "The return value from a function was an unknown value."
     --#ARGUMENTS {}
     --#SEVERITY WARNING
     --#TIMEINDEX 100
     --#STATE OPERATIONAL
::= 5749


hpevtEfiSysidBmcWarning TRAP-TYPE
     ENTERPRISE hpIpfE0Events
     VARIABLES { hpIpfEvtDetailStr }
     DESCRIPTION
        "EFI queries the BMC on the system board for the status of a system ID. The BMC could not complete the request successfully or on time. 
Data Field:  Internal EFI function status."

     --#SUMMARY "Cannot get system ID status from BMC"
     --#ARGUMENTS {}
     --#SEVERITY WARNING
     --#TIMEINDEX 100
     --#STATE OPERATIONAL
::= 5750


hpevtEfiSysidBmcReadError TRAP-TYPE
     ENTERPRISE hpIpfE0Events
     VARIABLES { hpIpfEvtDetailStr }
     DESCRIPTION
        "BMC reported a system ID status as inaccessible, reported invalid status or cannot return the current value of a system ID. 
Data Field: uuid status or internal EFI function status. 
System ID status: a 1 byte value 0 extended to 64bits: 
    0x00 -> primary and secondary values are valid 
    0x01 -> primary and secondary values are magic 
    0x02 -> primary and secondary values are inaccessible 
    0x04 -> primary and secondary values are invalid 
    0x08 -> primary and secondary values are null (UUID only) 
    0x10 -> primary and secondary values are different, value (primary or secondary) is valid 
    0x11 -> primary and secondary values are different, value (primary or secondary) is magic 
    0x12 -> primary and secondary values are different, value (primary or secondary) is inaccessible 
    0x14 -> primary and secondary values are different, value (primary or secondary) is invalid 
    0x18 -> primary and secondary values are different, value (primary or secondary) is null (UUID only)"

     --#SUMMARY "Cannot read a system ID"
     --#ARGUMENTS {}
     --#SEVERITY WARNING
     --#TIMEINDEX 100
     --#STATE OPERATIONAL
::= 5751


hpevtEfiSysidBmcWriteError TRAP-TYPE
     ENTERPRISE hpIpfE0Events
     VARIABLES { hpIpfEvtDetailStr }
     DESCRIPTION
        "Firmware tried to write a primary or secondary system ID as requested by the user during the boot sequence. The write failed. 
Data Field: Internal EFI function status."

     --#SUMMARY "Failed to write new system ID. BMC reported an error"
     --#ARGUMENTS {}
     --#SEVERITY WARNING
     --#TIMEINDEX 100
     --#STATE OPERATIONAL
::= 5752


hpevtEfiSysidInvalid TRAP-TYPE
     ENTERPRISE hpIpfE0Events
     VARIABLES { hpIpfEvtDetailStr }
     DESCRIPTION
        "The system ID(s) currently in the system is either invalid or, if the EFI_SYSID_BMC_WARNING, EFI_SYSID_BMC_READ_ERROR or EFI_SYSID_BMC_WRITE_ERROR events are also present, inaccessible to the system firmware. A stop boot condition will be generated and software license will probably be invalid. 
Data Field: 64-bit value.  
  If preceded by 0xbad00000000000 the following valid values are possible: 
    0000 -> valid UUID (should never see this one) 
    0001 -> magic UUID 
    0002 -> inaccessible UUID 
    0004 -> invalid (bad CRC) UUID
  If zero, then one of the following conditions occurred:
    Invalid combination of primary and secondary system ID values
    User declined copying/entering system ID values when prompted by firmware
  All other values indicate failure during attempt to update system IDs."

     --#SUMMARY "The system ID(s) currently in the system is invalid"
     --#ARGUMENTS {}
     --#SEVERITY WARNING
     --#TIMEINDEX 100
     --#STATE OPERATIONAL
::= 5753


hpevtEfiRtIvtEsiTableErr TRAP-TYPE
     ENTERPRISE hpIpfE0Events
     VARIABLES { hpIpfEvtDetailStr }
     DESCRIPTION
        "EFI is unable to find the SAL services for installing interrupt handlers.  EFI was trying to install the run-time handlers that are required for normal EFI booting.  EFI will be halting. 
Data Field:  internal EFI function status."

     --#SUMMARY "EFI unable to find the SAL services for installing interrupt handlers"
     --#ARGUMENTS {}
     --#SEVERITY CRITICAL
     --#TIMEINDEX 100
     --#STATE OPERATIONAL
::= 5755


hpevtEfiRtIvtEsiQueryErr TRAP-TYPE
     ENTERPRISE hpIpfE0Events
     VARIABLES { hpIpfEvtDetailStr }
     DESCRIPTION
        "EFI is unable to find the SAL service to install run-time interrupt handlers.  These handlers are required for normal EFI booting.  EFI will be halting. 
Data Field:  internal EFI function status."

     --#SUMMARY "EFI unable to find the SAL service to install run-time interrupt handlers"
     --#ARGUMENTS {}
     --#SEVERITY CRITICAL
     --#TIMEINDEX 100
     --#STATE OPERATIONAL
::= 5756


hpevtEfiBootIvtEsiTableErr TRAP-TYPE
     ENTERPRISE hpIpfE0Events
     VARIABLES { hpIpfEvtDetailStr }
     DESCRIPTION
        " EFI is unable to find the SAL services for installing interrupt handlers.  EFI was trying to install the boot-time handlers that are required for normal EFI booting.  EFI will be halting. 
Data Field:  internal EFI function status."

     --#SUMMARY "EFI unable to find the SAL services for installing interrupt handlers"
     --#ARGUMENTS {}
     --#SEVERITY CRITICAL
     --#TIMEINDEX 100
     --#STATE OPERATIONAL
::= 5757


hpevtEfiBootIvtEsiQueryErr TRAP-TYPE
     ENTERPRISE hpIpfE0Events
     VARIABLES { hpIpfEvtDetailStr }
     DESCRIPTION
        "EFI is unable to find the SAL service to install boot-time interrupt handlers.  These handlers are required for normal EFI booting.  EFI will be halting. 
Data Field:  internal EFI function status."

     --#SUMMARY "EFI unable to find the SAL service to install boot-time interrupt handlers"
     --#ARGUMENTS {}
     --#SEVERITY CRITICAL
     --#TIMEINDEX 100
     --#STATE OPERATIONAL
::= 5758


hpevtUtilitiesParmListTooLarge TRAP-TYPE
     ENTERPRISE hpIpfE0Events
     VARIABLES { hpIpfEvtDetailStr }
     DESCRIPTION
        "Too many parameters were passed in a request for the utilities system to perform an operation.  No more data is provided."

     --#SUMMARY "Too many parameters were passed to the utilities system"
     --#ARGUMENTS {}
     --#SEVERITY WARNING
     --#TIMEINDEX 100
     --#STATE OPERATIONAL
::= 5760


hpevtXbcPortPresenceError TRAP-TYPE
     ENTERPRISE hpIpfE0Events
     VARIABLES { hpIpfEvtDetailStr }
     DESCRIPTION
        "A crossbar port is expected to be present, but its presence detect bit is not set.  Data field bits 32:43 contain the crossbar ID,  bits 44:55 contain the port number for which the error occurred, and bits 0:31 contain the port status information."

     --#SUMMARY "A crossbar port is unexpectedly not present."
     --#ARGUMENTS {}
     --#SEVERITY CRITICAL
     --#TIMEINDEX 100
     --#STATE OPERATIONAL
::= 5762


hpevtXbcPortHwLinkError TRAP-TYPE
     ENTERPRISE hpIpfE0Events
     VARIABLES { hpIpfEvtDetailStr }
     DESCRIPTION
        "A crossbar port is expected to have its HW_LINK_OK bit set, but it is not.  Data field bits 32:43 contain the crossbar ID,  bits 44:55 contain the port number for which the error occurred, and bits 0:31 contain the port status information."

     --#SUMMARY "A crossbar port unexpectedly has its HW_LINK_OK bit not set."
     --#ARGUMENTS {}
     --#SEVERITY CRITICAL
     --#TIMEINDEX 100
     --#STATE OPERATIONAL
::= 5763


hpevtXbcPortFeError TRAP-TYPE
     ENTERPRISE hpIpfE0Events
     VARIABLES { hpIpfEvtDetailStr }
     DESCRIPTION
        "A connected crossbar port was found to have its FE bit set.  Data field bits 32:43 contain the crossbar ID,  bits 44:55 contain the port number for which the error occurred, and bits 0:31 contain the port status information."

     --#SUMMARY "A connected port was found to be in FE"
     --#ARGUMENTS {}
     --#SEVERITY CRITICAL
     --#TIMEINDEX 100
     --#STATE OPERATIONAL
::= 5764


hpevtXinLinkInitError TRAP-TYPE
     ENTERPRISE hpIpfE0Events
     VARIABLES { hpIpfEvtDetailStr }
     DESCRIPTION
        "There was an error while initializing the Cell Controller-Xbc interface.  The data field contains the address of the Cell Controller CSR for which the error occurred."

     --#SUMMARY "There was an error while initializing the Concorde-Xbc interface."
     --#ARGUMENTS {}
     --#SEVERITY CRITICAL
     --#TIMEINDEX 100
     --#STATE OPERATIONAL
::= 5766


hpevtXinLinkInitFailed TRAP-TYPE
     ENTERPRISE hpIpfE0Events
     VARIABLES { hpIpfEvtDetailStr }
     DESCRIPTION
        "The CC - XBC link failed to initialize."

     --#SUMMARY "The CC - XBC link failed to initialize."
     --#ARGUMENTS {}
     --#SEVERITY CRITICAL
     --#TIMEINDEX 100
     --#STATE OPERATIONAL
::= 5767


hpevtEfiGetMfgModeNotInit TRAP-TYPE
     ENTERPRISE hpIpfE0Events
     VARIABLES { hpIpfEvtDetailStr }
     DESCRIPTION
        "EFI is unable to determine current system mode.  The EFI/SAL interface is not initialized.  This interface should have been initialized before now.  This event indicates an internal EFI error.  EFI will continue executing."

     --#SUMMARY "Unable to determine system mode because EFI/SAL interface not initialized"
     --#ARGUMENTS {}
     --#SEVERITY WARNING
     --#TIMEINDEX 100
     --#STATE OPERATIONAL
::= 5768


hpevtEfiBmcMfgModeInvalid TRAP-TYPE
     ENTERPRISE hpIpfE0Events
     VARIABLES { hpIpfEvtDetailStr }
     DESCRIPTION
        "The BMC has returned an invalid system mode. 
Data Field:  the invalid mode.  Expected values are 0 or 1."

     --#SUMMARY "BMC returned an invalid system mode"
     --#ARGUMENTS {}
     --#SEVERITY WARNING
     --#TIMEINDEX 100
     --#STATE OPERATIONAL
::= 5769


hpevtEfiEnterMfgModeNotInit TRAP-TYPE
     ENTERPRISE hpIpfE0Events
     VARIABLES { hpIpfEvtDetailStr }
     DESCRIPTION
        "EFI is unable to specify a new system mode.  The EFI/SAL interface point is not initialized.  This interface should have been initialized before now.  This event indicates an internal EFI error.  EFI will continue executing in the current mode."

     --#SUMMARY "EFI unable to specify system mode because EFI/SAL interface not initialized"
     --#ARGUMENTS {}
     --#SEVERITY WARNING
     --#TIMEINDEX 100
     --#STATE OPERATIONAL
::= 5770


hpevtEfiExitMfgModeNotInit TRAP-TYPE
     ENTERPRISE hpIpfE0Events
     VARIABLES { hpIpfEvtDetailStr }
     DESCRIPTION
        "EFI is unable to enter normal system mode.  The EFI/SAL interface is not initialized.  This interface should have been initialized before now.  This event indicates an internal EFI error.  EFI will continue executing in the current mode."

     --#SUMMARY "Unable to enter normal system mode because EFI/SAL interface not initialized"
     --#ARGUMENTS {}
     --#SEVERITY WARNING
     --#TIMEINDEX 100
     --#STATE OPERATIONAL
::= 5771


hpevtEfiTaccessServiceNotInit TRAP-TYPE
     ENTERPRISE hpIpfE0Events
     VARIABLES { hpIpfEvtDetailStr }
     DESCRIPTION
        "EFI is unable to initialize part of the SAL/EFI interface.  This crucial service provides access to certain BMC functionality such as the security system.  EFI will halt. 
Data Field:  Return status from internal EFI function."

     --#SUMMARY "Unable to initialize part of the SAL/EFI interface"
     --#ARGUMENTS {}
     --#SEVERITY CRITICAL
     --#TIMEINDEX 100
     --#STATE OPERATIONAL
::= 5772


hpevtTreeNodeNotFound TRAP-TYPE
     ENTERPRISE hpIpfE0Events
     VARIABLES { hpIpfEvtDetailStr }
     DESCRIPTION
        "A needed tree node was not found.  The data field contains the ascii name of the tree node that was not found."

     --#SUMMARY "An expected tree node was not found"
     --#ARGUMENTS {}
     --#SEVERITY CRITICAL
     --#TIMEINDEX 100
     --#STATE OPERATIONAL
::= 5774


hpevtEfiSystemStateRunningErr TRAP-TYPE
     ENTERPRISE hpIpfE0Events
     VARIABLES { hpIpfEvtDetailStr }
     DESCRIPTION
        "EFI is unable to modify the system state from 'booting' to 'running'.  This is done as part of  Exit Boot Services.  The  system will not be able to enter a sleep mode. 
Data Field:   For errors, this data is zero.  For warnings, this data indicates the current system state as: 
   0  Error 
   1  booting 
   2  running 
   3  attention 
   4  fault 
   5  booting + attention"

     --#SUMMARY "EFI unable to modify system state to "running""
     --#ARGUMENTS {}
     --#SEVERITY WARNING
     --#TIMEINDEX 100
     --#STATE OPERATIONAL
::= 5776


hpevtPalBusConfigIncompatible TRAP-TYPE
     ENTERPRISE hpIpfE0Events
     VARIABLES { hpIpfEvtDetailStr }
     DESCRIPTION
        "CPUBusConfigValue setting in options as been compared with what is reported by PAL as settable and CPUBusConfigValue is specifying at least one bit that is not supported by this version of PAL using the Get Processor Bus Dependent Configuration Features. This chassis code is emmitted in pairs, the first data field contains the PAL expected values; the second data field contains the requested setting from options."

     --#SUMMARY "/options settings for CPUBusConfigValue aren't compatible with PAL"
     --#ARGUMENTS {}
     --#SEVERITY WARNING
     --#TIMEINDEX 100
     --#STATE OPERATIONAL
::= 5777


hpevtPalGetBusFeaturesFailed TRAP-TYPE
     ENTERPRISE hpIpfE0Events
     VARIABLES { hpIpfEvtDetailStr }
     DESCRIPTION
        "Firmware was unable to correctly issue the Get Processor Bus Dependent Configuration Features command."

     --#SUMMARY "The Get Processor Bus Dependent Configuration Features PAL call failed."
     --#ARGUMENTS {}
     --#SEVERITY WARNING
     --#TIMEINDEX 100
     --#STATE OPERATIONAL
::= 5778


hpevtMemDimmPairMismatch TRAP-TYPE
     ENTERPRISE hpIpfE0Events
     VARIABLES { hpIpfEvtDetailStr }
     DESCRIPTION
        "A pair of DIMMs installed in the system are mismatched, and that pair of DIMMs will not be used.  The data field indicates which pair of DIMMs are mismatched in the format 0x000000000000XBXA  where X is the number of the rank that is mismatched."

     --#SUMMARY "memory DIMM pair mismatch"
     --#ARGUMENTS {}
     --#SEVERITY WARNING
     --#TIMEINDEX 100
     --#STATE OPERATIONAL
::= 5779


hpevtEfiPosseLibNotInit TRAP-TYPE
     ENTERPRISE hpIpfE0Events
     VARIABLES { hpIpfEvtDetailStr }
     DESCRIPTION
        "EFI is unable to initialize internal library.  This collection of internal services is required for much of EFI's functionality.  EFI is halting."

     --#SUMMARY "EFI unable to initialize internal library"
     --#ARGUMENTS {}
     --#SEVERITY CRITICAL
     --#TIMEINDEX 100
     --#STATE OPERATIONAL
::= 5784


hpevtEfiSecurityNotInit TRAP-TYPE
     ENTERPRISE hpIpfE0Events
     VARIABLES { hpIpfEvtDetailStr }
     DESCRIPTION
        "EFI is unable to initialize the security level.  The privilege level of the system may or may not be Admin.  It is likely certain EFI facilities will be unavailable.  EFI will continue booting but security may be compromised. 
Data Field:  Return status from internal EFI function."

     --#SUMMARY "EFI unable to initialize security system"
     --#ARGUMENTS {}
     --#SEVERITY CRITICAL
     --#TIMEINDEX 100
     --#STATE OPERATIONAL
::= 5785


hpevtEfiSecInvalidSysmode TRAP-TYPE
     ENTERPRISE hpIpfE0Events
     VARIABLES { hpIpfEvtDetailStr }
     DESCRIPTION
        "EFI detected an invalid value for its internal privilege level.  This value is stored within SAL.  EFI will continue but system security may be compromised. 
Data Field:  The invalid privilege level."

     --#SUMMARY "EFI detected invalid internal privilege level"
     --#ARGUMENTS {}
     --#SEVERITY WARNING
     --#TIMEINDEX 100
     --#STATE OPERATIONAL
::= 5786


hpevtEfiSecSetPassLevelErr TRAP-TYPE
     ENTERPRISE hpIpfE0Events
     VARIABLES { hpIpfEvtDetailStr }
     DESCRIPTION
        "EFI detected an invalid privilege level when setting a BMC password.  Only the levels of Admin (0x30) and User (0x20) are permitted. 
Data Field:  the invalid privilege level."

     --#SUMMARY "EFI detected invalid privilege level when setting password"
     --#ARGUMENTS {}
     --#SEVERITY WARNING
     --#TIMEINDEX 100
     --#STATE OPERATIONAL
::= 5787


hpevtMdtBad TRAP-TYPE
     ENTERPRISE hpIpfE0Events
     VARIABLES { hpIpfEvtDetailStr }
     DESCRIPTION
        "SFW has determined that the Memory Data Table (MDT) table is invalid."

     --#SUMMARY "EFI MDT table is bad"
     --#ARGUMENTS {}
     --#SEVERITY CRITICAL
     --#TIMEINDEX 100
     --#STATE OPERATIONAL
::= 5788


hpevtBootCpuBadCoreFixedRatio TRAP-TYPE
     ENTERPRISE hpIpfE0Events
     VARIABLES { hpIpfEvtDetailStr }
     DESCRIPTION
        "Processor has incompatible fixed core ratio.
Data: Local CPU Number."

     --#SUMMARY "Processor has incompatible fixed core ratio"
     --#ARGUMENTS {}
     --#SEVERITY WARNING
     --#TIMEINDEX 100
     --#STATE OPERATIONAL
::= 5790


hpevtBootAllCpusSlatedForCompatDeconfig TRAP-TYPE
     ENTERPRISE hpIpfE0Events
     VARIABLES { hpIpfEvtDetailStr }
     DESCRIPTION
        "Data: A bitmask for which CPUs are slated to be deconfigured"

     --#SUMMARY "All processors slated for compatibility deconfiguration"
     --#ARGUMENTS {}
     --#SEVERITY CRITICAL
     --#TIMEINDEX 100
     --#STATE OPERATIONAL
::= 5791


hpevtXbcReadRemoteRouteError TRAP-TYPE
     ENTERPRISE hpIpfE0Events
     VARIABLES { hpIpfEvtDetailStr }
     DESCRIPTION
        "An error occurred while reading a crossbar remote route table, or an unxpected/invalid value was read from the table.  The data field consists of the crossbar ID (32:43), the port number of which the table was read (44:55), and the return status of the read call (0:32)."

     --#SUMMARY "An unexpected or invalid value was read from a crossbar remote route table."
     --#ARGUMENTS {}
     --#SEVERITY CRITICAL
     --#TIMEINDEX 100
     --#STATE OPERATIONAL
::= 5793


hpevtXbcReadNeighborInfoError TRAP-TYPE
     ENTERPRISE hpIpfE0Events
     VARIABLES { hpIpfEvtDetailStr }
     DESCRIPTION
        "An error occurred while trying to read the PORT[n]_NEIGHBOR_INFO crossbar CSR.  The data field consists of the crossbar ID (32:43) and port number (44:55) for which the CSR was read."

     --#SUMMARY "Error reading the PORT[n]_NEIGHBOR_INFO  XBC CSR."
     --#ARGUMENTS {}
     --#SEVERITY CRITICAL
     --#TIMEINDEX 100
     --#STATE OPERATIONAL
::= 5794


hpevtMemDimmQuadMismatch TRAP-TYPE
     ENTERPRISE hpIpfE0Events
     VARIABLES { hpIpfEvtDetailStr }
     DESCRIPTION
        "A quad of DIMMs installed in the system are mismatched, and that quad of DIMMs will not be used.  The data field indicates which quad of DIMMs are mismatched in the format 0x00000000XDXCXBXA  where X is the number of the rank that is mismatched."

     --#SUMMARY "memory DIMM quad mis-match"
     --#ARGUMENTS {}
     --#SEVERITY WARNING
     --#TIMEINDEX 100
     --#STATE OPERATIONAL
::= 5795


hpevtMemDimmFailed TRAP-TYPE
     ENTERPRISE hpIpfE0Events
     VARIABLES { hpIpfEvtDetailStr }
     DESCRIPTION
        "The DIMM at the physical location given by the data field had excessive errors and has been marked as 'FAILED' by firmware."

     --#SUMMARY "Firmware detected excessive errors on the DIMM."
     --#ARGUMENTS {}
     --#SEVERITY WARNING
     --#TIMEINDEX 100
     --#STATE OPERATIONAL
::= 5796


hpevtXbcPortOeError TRAP-TYPE
     ENTERPRISE hpIpfE0Events
     VARIABLES { hpIpfEvtDetailStr }
     DESCRIPTION
        "A XBC port was expected to be functional, but its OE bit was not set.  The data field consists of the contents of the port_status CSR (0:31), the XBC number (32:43), and the port number (44:55)."

     --#SUMMARY "The OE (output enable) bit was not set for a XBC port."
     --#ARGUMENTS {}
     --#SEVERITY CRITICAL
     --#TIMEINDEX 100
     --#STATE OPERATIONAL
::= 5797


hpevtXbcPortStatusError TRAP-TYPE
     ENTERPRISE hpIpfE0Events
     VARIABLES { hpIpfEvtDetailStr }
     DESCRIPTION
        "Unable to read the PORT_STATUS CSR for a XBC port.  The data field consists of the contents of the PORT_STATUS CSR (0:31), the XBC number (32:43), and the port number (44:55)."

     --#SUMMARY "An error occurred while trying to read the PORT_STATUS CSR for a XBC port."
     --#ARGUMENTS {}
     --#SEVERITY CRITICAL
     --#TIMEINDEX 100
     --#STATE OPERATIONAL
::= 5798


hpevtXbcPortLandmined TRAP-TYPE
     ENTERPRISE hpIpfE0Events
     VARIABLES { hpIpfEvtDetailStr }
     DESCRIPTION
        "A XBC port was unexpectedly found to be landmined.  The data field consists of the XBC number (32:43) and the port number (44:55)."

     --#SUMMARY "A XBC port was unexpectedly found to be landmined."
     --#ARGUMENTS {}
     --#SEVERITY CRITICAL
     --#TIMEINDEX 100
     --#STATE OPERATIONAL
::= 5799


hpevtPdIncompatibleCpuSpeeds TRAP-TYPE
     ENTERPRISE hpIpfE0Events
     VARIABLES { hpIpfEvtDetailStr }
     DESCRIPTION
        "Reporting cell tried to rendezvous with a cell with processors that are running at a different speed.  The data field lists the offending cell"

     --#SUMMARY "CPUs running at different speeds were detected during rendezvous"
     --#ARGUMENTS {}
     --#SEVERITY CRITICAL
     --#TIMEINDEX 100
     --#STATE OPERATIONAL
::= 5800


hpevtFabricCellLinkNotInit TRAP-TYPE
     ENTERPRISE hpIpfE0Events
     VARIABLES { hpIpfEvtDetailStr }
     DESCRIPTION
        "The link between the local CC and the local XBC is unexpectedly not initialized.  The data field is the XIN_LINK_STATE CC CSR value."

     --#SUMMARY "The link between the local CC and the local XBC is unexpectedly not initialized."
     --#ARGUMENTS {}
     --#SEVERITY CRITICAL
     --#TIMEINDEX 100
     --#STATE OPERATIONAL
::= 5802


hpevtFabricInvalidXbcNum TRAP-TYPE
     ENTERPRISE hpIpfE0Events
     VARIABLES { hpIpfEvtDetailStr }
     DESCRIPTION
        "A value that was expected to be a XBC number was found to be an invalid XBC number.  The data field is the invalid XBC number."

     --#SUMMARY "An invalid XBC number was given."
     --#ARGUMENTS {}
     --#SEVERITY CRITICAL
     --#TIMEINDEX 100
     --#STATE OPERATIONAL
::= 5803


hpevtFabricInvalidXbcPortNum TRAP-TYPE
     ENTERPRISE hpIpfE0Events
     VARIABLES { hpIpfEvtDetailStr }
     DESCRIPTION
        "A value that was expected to be a valid XBC port number was found to be invalid.  The data field is the XBC number (33:44) and the invalid XBC port number (44:55)."

     --#SUMMARY "An invalid XBC port number was given."
     --#ARGUMENTS {}
     --#SEVERITY CRITICAL
     --#TIMEINDEX 100
     --#STATE OPERATIONAL
::= 5804


hpevtUtilitiesLedParamError TRAP-TYPE
     ENTERPRISE hpIpfE0Events
     VARIABLES { hpIpfEvtDetailStr }
     DESCRIPTION
        "A bad parameter was passed to the utilities fuction that manipulates the LED on replacable parts.  The offending parameter is displayed in the data field."

     --#SUMMARY "A bad parameter was passed to the LED function in the utilities component"
     --#ARGUMENTS {}
     --#SEVERITY WARNING
     --#TIMEINDEX 100
     --#STATE OPERATIONAL
::= 5805


hpevtFabricUnexpectedNtype TRAP-TYPE
     ENTERPRISE hpIpfE0Events
     VARIABLES { hpIpfEvtDetailStr }
     DESCRIPTION
        "A neighbor type read from a XBC PORT_NEIGHBOR_INFO CSR was different than the expected neighbor type.  The data field contains the expected type (32:63) and the actual neighbor type (0:31)."

     --#SUMMARY "An unexpected neighbor type was read from a XBC PORT_NEIGHBOR_INFO CSR."
     --#ARGUMENTS {}
     --#SEVERITY CRITICAL
     --#TIMEINDEX 100
     --#STATE OPERATIONAL
::= 5806


hpevtFabricPortNotCc TRAP-TYPE
     ENTERPRISE hpIpfE0Events
     VARIABLES { hpIpfEvtDetailStr }
     DESCRIPTION
        "A XBC port number was unexpectedly found to not be a valid XBC-CC port.  The data field consists of the XBC number (32:43) and the port number (44:55)."

     --#SUMMARY "A given XBC port is not a valid XBC-CC port."
     --#ARGUMENTS {}
     --#SEVERITY CRITICAL
     --#TIMEINDEX 100
     --#STATE OPERATIONAL
::= 5807


hpevtFabricPortNotXbc TRAP-TYPE
     ENTERPRISE hpIpfE0Events
     VARIABLES { hpIpfEvtDetailStr }
     DESCRIPTION
        "A XBC port was unexpectedly found to be an invalid XBC-XBC port.  The data field consists of the XBC number (32:43) and the port number (44:55)."

     --#SUMMARY "A XBC port was unexpectedly found to be an invalid XBC-XBC port."
     --#ARGUMENTS {}
     --#SEVERITY CRITICAL
     --#TIMEINDEX 100
     --#STATE OPERATIONAL
::= 5808


hpevtFabricUnexpectedNChip TRAP-TYPE
     ENTERPRISE hpIpfE0Events
     VARIABLES { hpIpfEvtDetailStr }
     DESCRIPTION
        "The XBC neighbor chip number does not match the expected value for this topology.  The data field contains the expected neighbor chip number (32:63) and the actual neighbor chip number (0:31)."

     --#SUMMARY "The XBC neighbor chip number does not match the expected value for this topology"
     --#ARGUMENTS {}
     --#SEVERITY CRITICAL
     --#TIMEINDEX 100
     --#STATE OPERATIONAL
::= 5809


hpevtFabricUnexpectedNPort TRAP-TYPE
     ENTERPRISE hpIpfE0Events
     VARIABLES { hpIpfEvtDetailStr }
     DESCRIPTION
        "The XBC neighbor port number does not match the expected value for this topology.  The data field contains the expected neighbor port number (32:63) and the actual neighbor port number (0:31)."

     --#SUMMARY "The XBC neighbor port number does not match the expected value for this topology"
     --#ARGUMENTS {}
     --#SEVERITY CRITICAL
     --#TIMEINDEX 100
     --#STATE OPERATIONAL
::= 5810


hpevtBootNvmWriteToBmcTokenFailure TRAP-TYPE
     ENTERPRISE hpIpfE0Events
     VARIABLES { hpIpfEvtDetailStr }
     DESCRIPTION
        "A write to a BMC token has failed.  This is a boot warning condition.  Data: Upper 32 bits, BMC failure return code.  Lower 32 bits, BMC token number that failed."

     --#SUMMARY "Write through to BMC token failed"
     --#ARGUMENTS {}
     --#SEVERITY WARNING
     --#TIMEINDEX 100
     --#STATE OPERATIONAL
::= 5811


hpevtUtilitiesLedError TRAP-TYPE
     ENTERPRISE hpIpfE0Events
     VARIABLES { hpIpfEvtDetailStr }
     DESCRIPTION
        "The utilities system reported an error while trying to carry out the command to turn on, flash or turn off the LED.  The status returned by the command is displayed in the data field."

     --#SUMMARY "Utilities reported an error while trying to manipulate the LED"
     --#ARGUMENTS {}
     --#SEVERITY WARNING
     --#TIMEINDEX 100
     --#STATE OPERATIONAL
::= 5812


hpevtDuplicateCpuIds TRAP-TYPE
     ENTERPRISE hpIpfE0Events
     VARIABLES { hpIpfEvtDetailStr }
     DESCRIPTION
        "2 cpus think that they have the same ID within the cell.  Typically this would mean that PAL reported the same cpu id for more than 1 cpu on a bus.  The cpuid is in the data field."

     --#SUMMARY "Duplicate Cpu Ids were dectected within a cell."
     --#ARGUMENTS {}
     --#SEVERITY CRITICAL
     --#TIMEINDEX 100
     --#STATE OPERATIONAL
::= 5813


hpevtHp-uxCrashdumpStarted TRAP-TYPE
     ENTERPRISE hpIpfE0Events
     VARIABLES { hpIpfEvtDetailStr }
     DESCRIPTION
        "OS crashdump started (D700)"

     --#SUMMARY "OS crashdump started (D700)"
     --#ARGUMENTS {}
     --#SEVERITY WARNING
     --#TIMEINDEX 100
     --#STATE OPERATIONAL
::= 5823


hpevtHp-uxHexFaultCode TRAP-TYPE
     ENTERPRISE hpIpfE0Events
     VARIABLES { hpIpfEvtDetailStr }
     DESCRIPTION
        "OS legacy PA hex fault code (Bxxx). Possible I/O error or system panic"

     --#SUMMARY "OS legacy PA hex fault code (Bxxx)"
     --#ARGUMENTS {}
     --#SEVERITY CRITICAL
     --#TIMEINDEX 100
     --#STATE OPERATIONAL
::= 5824


hpevtHp-uxDumpStatus TRAP-TYPE
     ENTERPRISE hpIpfE0Events
     VARIABLES { hpIpfEvtDetailStr }
     DESCRIPTION
        "A memory dump occurred on the system, or on one
partition in a cellular system.  The dump occurred due to either a
non-recoverable error or by user request. EFxx is the OS dump status (the success/failure of the writing of the dump). EF00 = success (followed by either EF0A = successful dump with sync, or EF09 = successful dump without sync), EFFF = a general error, EFFE = dump path assertion failure, EFFD = no dump was taken by default, choice or failure, EFFC = dump was aborted by user."

     --#SUMMARY "OS dump status  (EFxx)"
     --#ARGUMENTS {}
     --#SEVERITY WARNING
     --#TIMEINDEX 100
     --#STATE OPERATIONAL
::= 5825


hpevtSettingProcTimeoutFail TRAP-TYPE
     ENTERPRISE hpIpfE0Events
     VARIABLES { hpIpfEvtDetailStr }
     DESCRIPTION
        "SFW has failed to set the processor timeout value via a PAL call. 
Data: PAL call return value."

     --#SUMMARY "Setting processor response timeout failed"
     --#ARGUMENTS {}
     --#SEVERITY WARNING
     --#TIMEINDEX 100
     --#STATE OPERATIONAL
::= 5827


hpevtEfiSecInitVerifyErr TRAP-TYPE
     ENTERPRISE hpIpfE0Events
     VARIABLES { hpIpfEvtDetailStr }
     DESCRIPTION
        "During EFI security initialization, the attempt to determine what privilege level a blank password provides, failed.  Most likely this indicates the BMC has failed.  EFI assumes that the BMC has failed and will attempt to continue booting.  Some EFI functionality may be unavailable. 
Data Field:  Return status from internal EFI function."

     --#SUMMARY "Unable to validate blank password during EFI security initialization"
     --#ARGUMENTS {}
     --#SEVERITY WARNING
     --#TIMEINDEX 100
     --#STATE OPERATIONAL
::= 5832


hpevtEfiSecInitCloseErr TRAP-TYPE
     ENTERPRISE hpIpfE0Events
     VARIABLES { hpIpfEvtDetailStr }
     DESCRIPTION
        "As part of normal security initialization, EFI attempted to issue a close session to the BMC (I.e. force the BMC to GUEST mode).  This attempt failed.  EFI is unable to initialize the security system.  EFI will continue but security may be compromised. 
Data Field:  Return status from internal EFI function."

     --#SUMMARY "Unable to enter Guest mode during EFI security initialization"
     --#ARGUMENTS {}
     --#SEVERITY WARNING
     --#TIMEINDEX 100
     --#STATE OPERATIONAL
::= 5833


hpevtEfiSecInitOpenErr TRAP-TYPE
     ENTERPRISE hpIpfE0Events
     VARIABLES { hpIpfEvtDetailStr }
     DESCRIPTION
        "As part of normal security initialization, EFI attempted to issue an open session to the BMC  in order to raise the privilege level to the highest permitted by a blank password.  This attempt failed.  EFI is unable to initialize the security system. 
Data Field:  Return status from internal EFI function."

     --#SUMMARY "Unable to increase privilege during EFI security initialization"
     --#ARGUMENTS {}
     --#SEVERITY WARNING
     --#TIMEINDEX 100
     --#STATE OPERATIONAL
::= 5834


hpevtEfiSecInitWriteErr TRAP-TYPE
     ENTERPRISE hpIpfE0Events
     VARIABLES { hpIpfEvtDetailStr }
     DESCRIPTION
        "As part of normal security initialization, EFI attempted to record the current privilege level.  This attempt failed.  EFI is unable to initialize the security system. 
Data Field:  Return status from internal EFI function."

     --#SUMMARY "EFI unable to write privilege level during security initialization"
     --#ARGUMENTS {}
     --#SEVERITY WARNING
     --#TIMEINDEX 100
     --#STATE OPERATIONAL
::= 5836


hpevtEfiSecInitWriteDenied TRAP-TYPE
     ENTERPRISE hpIpfE0Events
     VARIABLES { hpIpfEvtDetailStr }
     DESCRIPTION
        "As part of normal security initialization, EFI attempted to record the current privilege level.  This attempt failed with a privilege violation error.  EFI is unable to initialize the security system. 
Data Field:  Return status from internal EFI function."

     --#SUMMARY "EFI was denied permission to write the privilege level during security init"
     --#ARGUMENTS {}
     --#SEVERITY WARNING
     --#TIMEINDEX 100
     --#STATE OPERATIONAL
::= 5837


hpevtHp-uxDumpWriteError TRAP-TYPE
     ENTERPRISE hpIpfE0Events
     VARIABLES { hpIpfEvtDetailStr }
     DESCRIPTION
        "OS dump, error writing image area to disk (E055)"

     --#SUMMARY "OS dump, error writing image area to disk (E055)"
     --#ARGUMENTS {}
     --#SEVERITY WARNING
     --#TIMEINDEX 100
     --#STATE OPERATIONAL
::= 5853


hpevtErrDeadlockResetDetected TRAP-TYPE
     ENTERPRISE hpIpfE0Events
     VARIABLES { hpIpfEvtDetailStr }
     DESCRIPTION
        "Early in bootstrap, the coherency controller (CC) registers are checked for Deadlock Recovery Reset. This chassis code indicates that CC logs will be stored to NVRAM."

     --#SUMMARY "Coherency controller (CC) registers indicate a Deadlock Recovery Reset"
     --#ARGUMENTS {}
     --#SEVERITY CRITICAL
     --#TIMEINDEX 100
     --#STATE OPERATIONAL
::= 5896


hpevtMemParityErr TRAP-TYPE
     ENTERPRISE hpIpfE0Events
     VARIABLES { hpIpfEvtDetailStr }
     DESCRIPTION
        "SFW detected a memory address parity error.  The data field contains the physical location of DIMM that saw the parity error."

     --#SUMMARY "A memory address parity error has been detected. The physical location can be located in the data field."
     --#ARGUMENTS {}
     --#SEVERITY CRITICAL
     --#TIMEINDEX 100
     --#STATE OPERATIONAL
::= 6002


hpevtMemDimmLoadOrdErr TRAP-TYPE
     ENTERPRISE hpIpfE0Events
     VARIABLES { hpIpfEvtDetailStr }
     DESCRIPTION
        "The loading order of the DIMMs is incorrect. The cell is halted."

     --#SUMMARY "A DIMM loading order error has occurred"
     --#ARGUMENTS {}
     --#SEVERITY CRITICAL
     --#TIMEINDEX 100
     --#STATE OPERATIONAL
::= 6074


hpevtMemRefreshStartError TRAP-TYPE
     ENTERPRISE hpIpfE0Events
     VARIABLES { hpIpfEvtDetailStr }
     DESCRIPTION
        "Timeout Waiting for SDRAM parts to become ready - mem_status[0] Refresh Control Register"

     --#SUMMARY "Refresh Control Error Timeout"
     --#ARGUMENTS {}
     --#SEVERITY WARNING
     --#TIMEINDEX 100
     --#STATE OPERATIONAL
::= 6146


hpevtMemExtBaseboardIncompatible TRAP-TYPE
     ENTERPRISE hpIpfE0Events
     VARIABLES { hpIpfEvtDetailStr }
     DESCRIPTION
        "The version of Memory extender installed in the system has not been qualified to work with the version of the baseboard installed in the system."

     --#SUMMARY "memory extender/baseboard FRU mismatch"
     --#ARGUMENTS {}
     --#SEVERITY WARNING
     --#TIMEINDEX 100
     --#STATE OPERATIONAL
::= 6180


hpevtFabricDifferentTopologies TRAP-TYPE
     ENTERPRISE hpIpfE0Events
     VARIABLES { hpIpfEvtDetailStr }
     DESCRIPTION
        "There is a fabric topology mismatch with the XBCs in the complex.

Data Field:
   (Topology of XBC << 32) | Topology of destination XBC

   0x00   Topology not yet determined
   0x30   Domelight
   0x40   U-Turn (Left cabinet)
   0x41   U-Turn (Right cabinet)
   0x42   Cross-Flex
   0x43   U-Turn"

     --#SUMMARY "Fabric topology mismatch with XBCs in complex"
     --#ARGUMENTS {}
     --#SEVERITY CRITICAL
     --#TIMEINDEX 100
     --#STATE OPERATIONAL
::= 6730


hpevtFabricInvalidXbc2XbcPort TRAP-TYPE
     ENTERPRISE hpIpfE0Events
     VARIABLES { hpIpfEvtDetailStr }
     DESCRIPTION
        "While routing the XBC to XBC ports, an invalid port was encountered.  The data field is the crossbar number (32:43) and the port number (44:55)."

     --#SUMMARY "An invalid XBC to XBC port was found."
     --#ARGUMENTS {}
     --#SEVERITY WARNING
     --#TIMEINDEX 100
     --#STATE OPERATIONAL
::= 6795


hpevtFabricGetNeighborInfoError TRAP-TYPE
     ENTERPRISE hpIpfE0Events
     VARIABLES { hpIpfEvtDetailStr }
     DESCRIPTION
        "The XBC could not get neighbor information. 
 
Data Field: 
   XBC # << 32 | internal port attempting to access neighbor"

     --#SUMMARY "Could not get neighbor information."
     --#ARGUMENTS {}
     --#SEVERITY WARNING
     --#TIMEINDEX 100
     --#STATE OPERATIONAL
::= 7652


hpevtXbcRoutingErrorState TRAP-TYPE
     ENTERPRISE hpIpfE0Events
     VARIABLES { hpIpfEvtDetailStr }
     DESCRIPTION
        "For the XBC being routed, routing has already been attempted, but an error occurred.  Inspect chassis codes from other cells for more details regarding the nature of the problem.  The data field consists of the XBC number (32:63)"

     --#SUMMARY "The XBC's routing state was marked as in ERROR"
     --#ARGUMENTS {}
     --#SEVERITY CRITICAL
     --#TIMEINDEX 100
     --#STATE OPERATIONAL
::= 7653


hpevtNoNvmErrLogSpace TRAP-TYPE
     ENTERPRISE hpIpfE0Events
     VARIABLES { hpIpfEvtDetailStr }
     DESCRIPTION
        "This means that the error event log cannot be logged to the persistent storage. The data field gives the event type that was supposed to be logged."

     --#SUMMARY "It indicates that there is no NVM error space left for logging an Error Event."
     --#ARGUMENTS {}
     --#SEVERITY WARNING
     --#TIMEINDEX 100
     --#STATE OPERATIONAL
::= 7655


hpevtXbcPortError TRAP-TYPE
     ENTERPRISE hpIpfE0Events
     VARIABLES { hpIpfEvtDetailStr }
     DESCRIPTION
        "An XBC port was found to have an unexpected error.  The data field consists of the crossbar number (32:63) and the current port errors (0:31)"

     --#SUMMARY "An XBC port found to have an unexpected error."
     --#ARGUMENTS {}
     --#SEVERITY CRITICAL
     --#TIMEINDEX 100
     --#STATE OPERATIONAL
::= 7657


hpevtXbcPortRouteAround TRAP-TYPE
     ENTERPRISE hpIpfE0Events
     VARIABLES { hpIpfEvtDetailStr }
     DESCRIPTION
        "During fabric routing a port on a XBC was found in error or had been previously marked as in error. PDC will route around this XBC port. 
Data Field:   XBC number (32:63) and  external XBC port number (0:31)"

     --#SUMMARY "A XBC port route around has occurred"
     --#ARGUMENTS {}
     --#SEVERITY CRITICAL
     --#TIMEINDEX 100
     --#STATE OPERATIONAL
::= 7658


hpevtXbcUnexpectedState TRAP-TYPE
     ENTERPRISE hpIpfE0Events
     VARIABLES { hpIpfEvtDetailStr }
     DESCRIPTION
        "Data field:  the unexpected forward progress state (0:31) 
                   XBC number (32:44) 
                   Cell number (56:63)"

     --#SUMMARY "During routing a crossbar is found to be in an uexpected routing state."
     --#ARGUMENTS {}
     --#SEVERITY WARNING
     --#TIMEINDEX 100
     --#STATE OPERATIONAL
::= 7660


hpevtXbcRoutingStateTimeout TRAP-TYPE
     ENTERPRISE hpIpfE0Events
     VARIABLES { hpIpfEvtDetailStr }
     DESCRIPTION
        "A crossbar was found to be in an unexpected forward progress state during fabric routing.  This crossbar stayed in the unexpected state until Fabric Discovery timed out. 
Data fied: unexpected forward progress (0:31) 
                XBC number (32:44) 
               Cell number (56:63)"

     --#SUMMARY "An unexpected XBC forward progress state was continually found until timing out."
     --#ARGUMENTS {}
     --#SEVERITY WARNING
     --#TIMEINDEX 100
     --#STATE OPERATIONAL
::= 7661


hpevtXbcNeighborPortNotRoutable TRAP-TYPE
     ENTERPRISE hpIpfE0Events
     VARIABLES { hpIpfEvtDetailStr }
     DESCRIPTION
        "An XBC port was found that is not healthy.  This indicates at least one of the following about the port: 
- Hardware link is not okay 
- Presence detect is false 
- Fatal error detected 
- SBE detected 
- LPE detected 
- Port landmined 
 
The data field of the chassis code indicates which port is unhealthy, as well as the fabric routing state before the problem was encountered."

     --#SUMMARY "During remote routing, the current port's neighbor is not healthy."
     --#ARGUMENTS {}
     --#SEVERITY CRITICAL
     --#TIMEINDEX 100
     --#STATE OPERATIONAL
::= 7663


hpevtFabricCcToXbcError TRAP-TYPE
     ENTERPRISE hpIpfE0Events
     VARIABLES { hpIpfEvtDetailStr }
     DESCRIPTION
        "The CC to XBC link is not viable."

     --#SUMMARY "The CC to XBC link is not viable."
     --#ARGUMENTS {}
     --#SEVERITY CRITICAL
     --#TIMEINDEX 100
     --#STATE OPERATIONAL
::= 7664


hpevtFabricRouteXbcError TRAP-TYPE
     ENTERPRISE hpIpfE0Events
     VARIABLES { hpIpfEvtDetailStr }
     DESCRIPTION
        "There was a problem performing remote routing on the local XBC.  Chassis codes sent before this one may provide more details about the exact nature of the problem.  The data field consists of the XBC number that failed routing (32:63)"

     --#SUMMARY "Remote routing a crossbar failed."
     --#ARGUMENTS {}
     --#SEVERITY CRITICAL
     --#TIMEINDEX 100
     --#STATE OPERATIONAL
::= 7666


hpevtFabricMaxBrokenLinks TRAP-TYPE
     ENTERPRISE hpIpfE0Events
     VARIABLES { hpIpfEvtDetailStr }
     DESCRIPTION
        "Two or more XBC-XBC links were found to be broken.  The data field is the XBC number (32:63) and a bit map of the ports broken (0:31)"

     --#SUMMARY "Too many XBC-to-XBC were broken in the complex."
     --#ARGUMENTS {}
     --#SEVERITY CRITICAL
     --#TIMEINDEX 100
     --#STATE OPERATIONAL
::= 7667


hpevtXbcSemaphoreTakeoverFailed TRAP-TYPE
     ENTERPRISE hpIpfE0Events
     VARIABLES { hpIpfEvtDetailStr }
     DESCRIPTION
        "After unlocking the XBC Global Semaphore for a takeover, this cell did not get the semaphore."

     --#SUMMARY "This cell did not get the XBC Global Semaphore."
     --#ARGUMENTS {}
     --#SEVERITY CRITICAL
     --#TIMEINDEX 100
     --#STATE OPERATIONAL
::= 7669


hpevtXbcForceUnlockSm4Timeout TRAP-TYPE
     ENTERPRISE hpIpfE0Events
     VARIABLES { hpIpfEvtDetailStr }
     DESCRIPTION
        "When a cell holds an XBC semaphore for an extended period of time, fabric will attempt to takeover the semaphore so that the rest of the cells will have access to it.  Fabric will  attempt to take the SM4 for a period of time.  If it is unable to unlock the SM4 within the timeout period, it will send this chassis code and halt the cell. 
Data field:  XBC number (32:63) and current owner (cell) of the semaphore (0:31)"

     --#SUMMARY "Attempted an XBC SM4 takeover and timed out trying to unlock the SM4."
     --#ARGUMENTS {}
     --#SEVERITY CRITICAL
     --#TIMEINDEX 100
     --#STATE OPERATIONAL
::= 7671


hpevtXbcGetGlobalSm4Timeout TRAP-TYPE
     ENTERPRISE hpIpfE0Events
     VARIABLES { hpIpfEvtDetailStr }
     DESCRIPTION
        "During Fabric Discovery, the cell will wait until it gets the XBC's Global Semaphore.  It waits for a very long time.  This chassis code indicates that the wait has timed out."

     --#SUMMARY "Waiting for the XBC Global Semaphore has timed out."
     --#ARGUMENTS {}
     --#SEVERITY CRITICAL
     --#TIMEINDEX 100
     --#STATE OPERATIONAL
::= 7673


hpevtXbcReleaseSm4Timeout TRAP-TYPE
     ENTERPRISE hpIpfE0Events
     VARIABLES { hpIpfEvtDetailStr }
     DESCRIPTION
        "The XBC Release Semaphore timeout is designed to fail last.  The semaphore could not be released.  Any other cell (even outside the PD) may be blocked because the XBC is a global resource. 
Data field:  current semaphore owner (0:31) 
                  XBC number (32:43) 
                  port number (44:55) 
                  cell number (56:63)"

     --#SUMMARY "A timeout occurred while attempting to release the XBC semaphore."
     --#ARGUMENTS {}
     --#SEVERITY CRITICAL
     --#TIMEINDEX 100
     --#STATE OPERATIONAL
::= 7674


hpevtMpBatteryFailure TRAP-TYPE
     ENTERPRISE hpIpfE0Events
     VARIABLES { hpIpfEvtDetailStr }
     DESCRIPTION
        "Management Processor Firmware detected improper data in NVRAM (bad checksums.)  Either the NVRAM layout changed, or the Management Processor Battery may not be maintaining the data through A/C power cycles."

     --#SUMMARY "Management Processor Firmware Battery Failure or NVRAM change"
     --#ARGUMENTS {}
     --#SEVERITY WARNING
     --#TIMEINDEX 100
     --#STATE OPERATIONAL
::= 7684


hpevtMpSoftwareError TRAP-TYPE
     ENTERPRISE hpIpfE0Events
     VARIABLES { hpIpfEvtDetailStr }
     DESCRIPTION
        "Management Processor Firmware detected a software error and is logging an event.  The data represents data associated with the error seen."

     --#SUMMARY "Management Processor Firmware Software Error"
     --#ARGUMENTS {}
     --#SEVERITY WARNING
     --#TIMEINDEX 100
     --#STATE OPERATIONAL
::= 7685


hpevtMpI2cCommError TRAP-TYPE
     ENTERPRISE hpIpfE0Events
     VARIABLES { hpIpfEvtDetailStr }
     DESCRIPTION
        "An I2C Communication failure with the Baseboard Management Controller  was detected.  Without I2C communication, the system cannot be powered on/off or reset."

     --#SUMMARY "Management Processor detected an I2C Communication Error with BMC."
     --#ARGUMENTS {}
     --#SEVERITY WARNING
     --#TIMEINDEX 100
     --#STATE OPERATIONAL
::= 7686


hpevtRomCrcError TRAP-TYPE
     ENTERPRISE hpIpfE0Events
     VARIABLES { hpIpfEvtDetailStr }
     DESCRIPTION
        "A stored CRC value did not match the calculated CRC value for the specified address."

     --#SUMMARY "A CRC error was discovered when verifying the ROM"
     --#ARGUMENTS {}
     --#SEVERITY CRITICAL
     --#TIMEINDEX 100
     --#STATE OPERATIONAL
::= 7690


hpevtIoIdentifyIoBpFailed TRAP-TYPE
     ENTERPRISE hpIpfE0Events
     VARIABLES { hpIpfEvtDetailStr }
     DESCRIPTION
        "See Summary."

     --#SUMMARY "(HWE)  IO backplane type unknown"
     --#ARGUMENTS {}
     --#SEVERITY WARNING
     --#TIMEINDEX 100
     --#STATE OPERATIONAL
::= 7718


hpevtCpuRevisionMismatch TRAP-TYPE
     ENTERPRISE hpIpfE0Events
     VARIABLES { hpIpfEvtDetailStr }
     DESCRIPTION
        "2 cpus in the system are reporting different revisions.  This event will be emitted in greoups of 3 with the two revisions reported in the first 2 data fields and the cpu number in the 3rd data field."

     --#SUMMARY "CPU Revisions did not match"
     --#ARGUMENTS {}
     --#SEVERITY CRITICAL
     --#TIMEINDEX 100
     --#STATE OPERATIONAL
::= 7732


hpevtCpuFreqMismatch TRAP-TYPE
     ENTERPRISE hpIpfE0Events
     VARIABLES { hpIpfEvtDetailStr }
     DESCRIPTION
        "This chassis code will be emitted in pairs.  2 cpus are reporting that they are running at different frequencies.  The two frequencies are reported in the data fields."

     --#SUMMARY "2 cpus are running at mismatched frequencies."
     --#ARGUMENTS {}
     --#SEVERITY CRITICAL
     --#TIMEINDEX 100
     --#STATE OPERATIONAL
::= 7733


hpevtCpuOverclocked TRAP-TYPE
     ENTERPRISE hpIpfE0Events
     VARIABLES { hpIpfEvtDetailStr }
     DESCRIPTION
        "The rating for the cpu and the actual speed will be emitted in 2 sequencial event data fields."

     --#SUMMARY "A cpu is being overclocked"
     --#ARGUMENTS {}
     --#SEVERITY CRITICAL
     --#TIMEINDEX 100
     --#STATE OPERATIONAL
::= 7734


hpevtCmplxProfilIncoherent TRAP-TYPE
     ENTERPRISE hpIpfE0Events
     VARIABLES { hpIpfEvtDetailStr }
     DESCRIPTION
        "The complex profile is stored in NVRAM on the MP and each cell. All copies must match. For this error to be generated, not only is the MP's copy of the complex profile invalid, but not all of the cell's copies match."

     --#SUMMARY "Copy of complex profile on sub and cells don't match"
     --#ARGUMENTS {}
     --#SEVERITY CRITICAL
     --#TIMEINDEX 100
     --#STATE OPERATIONAL
::= 7758


hpevtDuplicateCabinet TRAP-TYPE
     ENTERPRISE hpIpfE0Events
     VARIABLES { hpIpfEvtDetailStr }
     DESCRIPTION
        "The MP detected 2 or more cabinets with the same cabinet number."

     --#SUMMARY "Duplicate cabinet number detected"
     --#ARGUMENTS {}
     --#SEVERITY CRITICAL
     --#TIMEINDEX 100
     --#STATE OPERATIONAL
::= 7760


hpevtIdCommandRequired TRAP-TYPE
     ENTERPRISE hpIpfE0Events
     VARIABLES { hpIpfEvtDetailStr }
     DESCRIPTION
        "The complex identification information in group A of the complex profile is invalid. The MP (Managability Processor) command 'ID' must be run. The SSKEY hardware is required."

     --#SUMMARY "MP ID command must be run"
     --#ARGUMENTS {}
     --#SEVERITY CRITICAL
     --#TIMEINDEX 100
     --#STATE OPERATIONAL
::= 7767


hpevtNvramBatteryFail TRAP-TYPE
     ENTERPRISE hpIpfE0Events
     VARIABLES { hpIpfEvtDetailStr }
     DESCRIPTION
        "The battery on the SBCH is below the safe threshold. The battery can be replaced online."

     --#SUMMARY "MP Battery is low"
     --#ARGUMENTS {}
     --#SEVERITY WARNING
     --#TIMEINDEX 100
     --#STATE OPERATIONAL
::= 7771


hpevtPartitionTimeoutReset TRAP-TYPE
     ENTERPRISE hpIpfE0Events
     VARIABLES { hpIpfEvtDetailStr }
     DESCRIPTION
        "The partition is being reset because its  watchdog timer expired and automatic restart is enabled."

     --#SUMMARY "Partition being reset due to watchdog timeout expiring"
     --#ARGUMENTS {}
     --#SEVERITY CRITICAL
     --#TIMEINDEX 100
     --#STATE OPERATIONAL
::= 7773


hpevtPdhcWatchdogTimedOut TRAP-TYPE
     ENTERPRISE hpIpfE0Events
     VARIABLES { hpIpfEvtDetailStr }
     DESCRIPTION
        "The processor dependent hardware controller (PDHC) on the cell board had its watchdog timer expire. The PDHC will reset the watchdog as the main program runs. If the watchdog does not get reset within 7 seconds the timer will expire, resetting the PDHC."

     --#SUMMARY "PDHC FW was reset by hardware due to firmware inactivity."
     --#ARGUMENTS {}
     --#SEVERITY WARNING
     --#TIMEINDEX 100
     --#STATE OPERATIONAL
::= 7774


hpevtAbortPowerupOth TRAP-TYPE
     ENTERPRISE hpIpfE0Events
     VARIABLES { hpIpfEvtDetailStr }
     DESCRIPTION
        "The Cabinet Power Up request was aborted due to ambient air over temperature."

     --#SUMMARY "Power Up Aborted, Over Temp"
     --#ARGUMENTS {}
     --#SEVERITY WARNING
     --#TIMEINDEX 100
     --#STATE OPERATIONAL
::= 7781


hpevtAbortPwrupBps TRAP-TYPE
     ENTERPRISE hpIpfE0Events
     VARIABLES { hpIpfEvtDetailStr }
     DESCRIPTION
        "The power requirements for the cabinet exceeds the capabilities of the available Bulk Power Supplies. The PM3 section of the Utilities Subsystems keeps a tally of the power requirements for all installed entities in a cabinet. The power available from the Bulk Power Supplies does not meet the requirements of the installed entities, according to the Cabinet Power Tally."

     --#SUMMARY "Too Few Bulk Power Supplies Available"
     --#ARGUMENTS {}
     --#SEVERITY CRITICAL
     --#TIMEINDEX 100
     --#STATE OPERATIONAL
::= 7782


hpevtAbortStartBlowr TRAP-TYPE
     ENTERPRISE hpIpfE0Events
     VARIABLES { hpIpfEvtDetailStr }
     DESCRIPTION
        "When given a power up request, the cabinet had to abort the start up due to less than the required number of Cabinet Blowers installed."

     --#SUMMARY "No Cabinet Start, Insufficient Blowers"
     --#ARGUMENTS {}
     --#SEVERITY CRITICAL
     --#TIMEINDEX 100
     --#STATE OPERATIONAL
::= 7783


hpevtAbortStartIofan TRAP-TYPE
     ENTERPRISE hpIpfE0Events
     VARIABLES { hpIpfEvtDetailStr }
     DESCRIPTION
        "When given a power up request, the cabinet had to abort the start up due to less than the required number of IO fans present."

     --#SUMMARY "No Cabinet Start, Insufficient IO Fans"
     --#ARGUMENTS {}
     --#SEVERITY CRITICAL
     --#TIMEINDEX 100
     --#STATE OPERATIONAL
::= 7784


hpevtAcDeleted TRAP-TYPE
     ENTERPRISE hpIpfE0Events
     VARIABLES { hpIpfEvtDetailStr }
     DESCRIPTION
        "The AC power connected to the PDCA (Power Distribution Control Assembly) was removed. The data field contains the physical location of the PDCA. 
 
The PDCA source that was deleted can be identified by the implementation dependent field (data byte 3) of the physical location: 
 
   data byte[3]: 0 for PDCA 0, 1 for PDCA 1."

     --#SUMMARY "AC power to the PDCA was removed. Data Byte 3 specifies PDCA number."
     --#ARGUMENTS {}
     --#SEVERITY WARNING
     --#TIMEINDEX 100
     --#STATE OPERATIONAL
::= 7786


hpevtBlowrFail TRAP-TYPE
     ENTERPRISE hpIpfE0Events
     VARIABLES { hpIpfEvtDetailStr }
     DESCRIPTION
        "A cabinet main blower has failed. Depending on the number of blowers still operating, the cabinet may or may not shut down. View the Error Log entries to determine if the cabinet is operating. 
 
If many log entries call out entities powering off during the same time frame  as this BLOWR_FAIL, the cabinet has probably shutdown.  Carefully review the log for the first few events within the same time frame for the root cause of the problem. The GSP command, PS, will show a detailed power status for a cabinet. If the +48V LED on the Front Panel Board is not lit, power is not enabled to the cabinet. This is an indication the cabinet blowers have probably gone from N to N - 1 status requiring an immediate cabinet shutdown."

     --#SUMMARY "Cabinet Main Blower Failed"
     --#ARGUMENTS {}
     --#SEVERITY WARNING
     --#TIMEINDEX 100
     --#STATE OPERATIONAL
::= 7791


hpevtBpsFail48flt TRAP-TYPE
     ENTERPRISE hpIpfE0Events
     VARIABLES { hpIpfEvtDetailStr }
     DESCRIPTION
        "A 48 Volt DC Converter powered by the specified PDCA failed on the designated Bulk Power Supply.  
 
The PDCA powering the converter on the BPS that failed can be identified by the implementation dependent field (data byte 3) of the BPS' physical location: 
 
   data byte[3]: 0 for PDCA 0, 1 for PDCA 1."

     --#SUMMARY "48 Volt Converter Failed. Data Byte 3 specifies PDCA number."
     --#ARGUMENTS {}
     --#SEVERITY WARNING
     --#TIMEINDEX 100
     --#STATE OPERATIONAL
::= 7793


hpevtBpsFailFanflt TRAP-TYPE
     ENTERPRISE hpIpfE0Events
     VARIABLES { hpIpfEvtDetailStr }
     DESCRIPTION
        "The designated Bulk Power Supply is reporting its fan has failed.   "

     --#SUMMARY "Fan failed in designated Bulk Power Supply"
     --#ARGUMENTS {}
     --#SEVERITY WARNING
     --#TIMEINDEX 100
     --#STATE OPERATIONAL
::= 7795


hpevtBpsFailOt TRAP-TYPE
     ENTERPRISE hpIpfE0Events
     VARIABLES { hpIpfEvtDetailStr }
     DESCRIPTION
        "The 48 Volt DC Converter powered by the specified PDCA in the designated Bulk Power Supply, is in over temp condition. 
 
The PDCA powering the converter on the BPS that failed can be identified by the activity status (last byte of chassis code): 
   e = PDCA 1 
   f = PDCA 0"

     --#SUMMARY "1 Side Converter Over Temp"
     --#ARGUMENTS {}
     --#SEVERITY WARNING
     --#TIMEINDEX 100
     --#STATE OPERATIONAL
::= 7796


hpevtBpsNotRedundant TRAP-TYPE
     ENTERPRISE hpIpfE0Events
     VARIABLES { hpIpfEvtDetailStr }
     DESCRIPTION
        "The number of functioning Bulk Power Supplies has decreased to where the Cabinet Power supplied (number of available Bulk Power Supplies times power output per each) minus the estimated Cabinet Power consumed is greater than 0, but less than the output of one Bulk Power Supply."

     --#SUMMARY "Bulk Power Supplies are not Redundant."
     --#ARGUMENTS {}
     --#SEVERITY WARNING
     --#TIMEINDEX 100
     --#STATE OPERATIONAL
::= 7798


hpevtBpsOvervoltage TRAP-TYPE
     ENTERPRISE hpIpfE0Events
     VARIABLES { hpIpfEvtDetailStr }
     DESCRIPTION
        "The PM has detected the value of +48V power, as measured on the UGUY board, has exceeded an upper threshold."

     --#SUMMARY "+48V DC has exceeded its upper limit"
     --#ARGUMENTS {}
     --#SEVERITY CRITICAL
     --#TIMEINDEX 100
     --#STATE OPERATIONAL
::= 7799


hpevtBpsUndervoltage TRAP-TYPE
     ENTERPRISE hpIpfE0Events
     VARIABLES { hpIpfEvtDetailStr }
     DESCRIPTION
        "The PM has detected the value of +48V power, as measured on the UGUY board, has fallen below a lower threshold."

     --#SUMMARY "+48V DC has fallen below its lower limit"
     --#ARGUMENTS {}
     --#SEVERITY CRITICAL
     --#TIMEINDEX 100
     --#STATE OPERATIONAL
::= 7803


hpevtCabFanFail TRAP-TYPE
     ENTERPRISE hpIpfE0Events
     VARIABLES { hpIpfEvtDetailStr }
     DESCRIPTION
        "A cabinet fan has failed. Depending on the number of cabinet fans still operating, the cabinet may or may not shut down. View the Error Log entries to determine if the cabinet is operating."

     --#SUMMARY "Cabinet Fan Failed"
     --#ARGUMENTS {}
     --#SEVERITY WARNING
     --#TIMEINDEX 100
     --#STATE OPERATIONAL
::= 7806


hpevtHkpOvervoltage TRAP-TYPE
     ENTERPRISE hpIpfE0Events
     VARIABLES { hpIpfEvtDetailStr }
     DESCRIPTION
        "Housekeeping power has exceeded expected levels."

     --#SUMMARY "Housekeeping power has exceeded expected levels."
     --#ARGUMENTS {}
     --#SEVERITY CRITICAL
     --#TIMEINDEX 100
     --#STATE OPERATIONAL
::= 7822


hpevtHkpUndervoltage TRAP-TYPE
     ENTERPRISE hpIpfE0Events
     VARIABLES { hpIpfEvtDetailStr }
     DESCRIPTION
        "Housekeeping power has fallen below expected levels."

     --#SUMMARY "Housekeeping power has fallen below expected levels."
     --#ARGUMENTS {}
     --#SEVERITY CRITICAL
     --#TIMEINDEX 100
     --#STATE OPERATIONAL
::= 7823


hpevtIllegalBpsCfgOrPhaseFlt TRAP-TYPE
     ENTERPRISE hpIpfE0Events
     VARIABLES { hpIpfEvtDetailStr }
     DESCRIPTION
        "Through failures or reconfiguration, the BPS for the cabinet named are illegally configured. There must be a BPS connected to each phase of the power. Phase 1 feeds BPS slots 0 & 1, phase 2 feeds slots 2 & 3, and phase 3 feeds 4 & 5. There must be a BPS connected to each phase. If 4 BPS are installed in a cabinet in slots 0 - 3 and 4 & 5 were empty, this would be an illegal configuration. They should be installed in 0,1,2,and 4 or 0,1,3,and 5 or some combination thereof.  
 
The PDCA physical location determines which phase is configured incorrectly. 
 
Data Byte 3 (implementation dependent field) indicates the PDCA number used when the configuration error occurred:"

     --#SUMMARY "The BPSs for the cabinet are illegally configured. Data Byte 3 = PDCA number."
     --#ARGUMENTS {}
     --#SEVERITY WARNING
     --#TIMEINDEX 100
     --#STATE OPERATIONAL
::= 7824


hpevtIllegalBpsid TRAP-TYPE
     ENTERPRISE hpIpfE0Events
     VARIABLES { hpIpfEvtDetailStr }
     DESCRIPTION
        "A Bulk Power Supply is reporting an unknown BPS ID. The Bulk Power Supply will not be powered up and added to the Power Available tally.  If cabinet is not powered up, it will refuse to power up until this fault is corrected."

     --#SUMMARY "BPS ID received from installed Bulk Power Supply was unknown"
     --#ARGUMENTS {}
     --#SEVERITY WARNING
     --#TIMEINDEX 100
     --#STATE OPERATIONAL
::= 7825


hpevtInletOvertempHi TRAP-TYPE
     ENTERPRISE hpIpfE0Events
     VARIABLES { hpIpfEvtDetailStr }
     DESCRIPTION
        "The cabinet's Ambient Air Sensor detected a change in air temperature entering the over-temp-high range. The Cabinet will be shutting itself down to prevent component damage."

     --#SUMMARY "Ambient Air Sensor Overtemp Warning"
     --#ARGUMENTS {}
     --#SEVERITY CRITICAL
     --#TIMEINDEX 100
     --#STATE OPERATIONAL
::= 7827


hpevtInletOvertempLo TRAP-TYPE
     ENTERPRISE hpIpfE0Events
     VARIABLES { hpIpfEvtDetailStr }
     DESCRIPTION
        "The cabinet's Ambient Air Sensor detected a change in air temperature crossing to the low range. The air temperature may be rising or falling.  This is just a reporting of entering the over-temp-low range."

     --#SUMMARY "Ambient Air Sensor Overtemp Warning"
     --#ARGUMENTS {}
     --#SEVERITY WARNING
     --#TIMEINDEX 100
     --#STATE OPERATIONAL
::= 7828


hpevtInletOvertempMid TRAP-TYPE
     ENTERPRISE hpIpfE0Events
     VARIABLES { hpIpfEvtDetailStr }
     DESCRIPTION
        "The cabinet's Ambient Air Sensor detected a change in air temperature crossing to the mid range. The air temperature may be rising or falling.  This is just a reporting of entering the over-temp-mid range.."

     --#SUMMARY "Ambient Air Sensor Overtemp Warning"
     --#ARGUMENTS {}
     --#SEVERITY WARNING
     --#TIMEINDEX 100
     --#STATE OPERATIONAL
::= 7829


hpevtIofanFail TRAP-TYPE
     ENTERPRISE hpIpfE0Events
     VARIABLES { hpIpfEvtDetailStr }
     DESCRIPTION
        "An IO Chassis cooling fan has failed.  Depending on the number of fans still operating, the cabinet may or may not shut down. View Error Log entries to determine if the cabinet is operating. If many log entries call out entities powering off during the same time frame as this IOFAN_FAIL, the cabinet has probably shutdown. Carefully review the log for the first few events within the same time frame for the root cause of the problem. The Guardian Service Processor command, PS, will show a detailed power status for a cabinet. The +48V LED on the Front Panel Board not lit, power is not enabled to the cabinet, indicating the cabinet IO Chassis fans have probably gone from N to N - 1 status requiring an immediate cabinet shutdown."

     --#SUMMARY "IO Fan Failed"
     --#ARGUMENTS {}
     --#SEVERITY WARNING
     --#TIMEINDEX 100
     --#STATE OPERATIONAL
::= 7836


hpevtPowerOverload TRAP-TYPE
     ENTERPRISE hpIpfE0Events
     VARIABLES { hpIpfEvtDetailStr }
     DESCRIPTION
        "This code is issued when the Cabinet Power supplied (number of Bulk Power Supplies times power output per each) minus the estimated Cabinet Power consumed drops below 0. Utilities firmware will not allow a cabinet in this state to power up (see ABORT_PWRUP_BPS). Utilities firmware will not shut down a cabinet in this state. However, there is a possibility of a cabinet brownout, making the cabinet unreliable."

     --#SUMMARY "Cabinet Power System is in overload."
     --#ARGUMENTS {}
     --#SEVERITY WARNING
     --#TIMEINDEX 100
     --#STATE OPERATIONAL
::= 7842


hpevtShutdownBlowr TRAP-TYPE
     ENTERPRISE hpIpfE0Events
     VARIABLES { hpIpfEvtDetailStr }
     DESCRIPTION
        "After a BLOWR_FAIL, there were N-1 blowers functioning. This is an illegal condition causing immediate cabinet shutdown to prevent component damage."

     --#SUMMARY "Cabinet Shutdown - Insufficient Blowers"
     --#ARGUMENTS {}
     --#SEVERITY CRITICAL
     --#TIMEINDEX 100
     --#STATE OPERATIONAL
::= 7845


hpevtShutdownIofan TRAP-TYPE
     ENTERPRISE hpIpfE0Events
     VARIABLES { hpIpfEvtDetailStr }
     DESCRIPTION
        "After a IOFAN_FAIL, there were N-1 fans functioning. This is an illegal condition causing immediate cabinet shutdown to prevent component damage."

     --#SUMMARY "Cabinet Shutdown - Insufficient IO Fans"
     --#ARGUMENTS {}
     --#SEVERITY CRITICAL
     --#TIMEINDEX 100
     --#STATE OPERATIONAL
::= 7846


hpevtXucFanFail TRAP-TYPE
     ENTERPRISE hpIpfE0Events
     VARIABLES { hpIpfEvtDetailStr }
     DESCRIPTION
        "One of  two fans in the Utility chassis of the IO Expansion Cabinet has failed."

     --#SUMMARY "IO Expansion Utility Cabinet Fan Failed"
     --#ARGUMENTS {}
     --#SEVERITY WARNING
     --#TIMEINDEX 100
     --#STATE OPERATIONAL
::= 7849


hpevtCluWatchdogReset TRAP-TYPE
     ENTERPRISE hpIpfE0Events
     VARIABLES { hpIpfEvtDetailStr }
     DESCRIPTION
        "The Watchdog Timer checks for inactivity, or hung state, of the Cabinet Level Utilities (CLU) portion of the UGUY. During activity, the timer is continually reset. If the timer expires, it will automatically reset the CLU microprocessor. This will not affect running partitions."

     --#SUMMARY "Watchdog Timer Expired"
     --#ARGUMENTS {}
     --#SEVERITY CRITICAL
     --#TIMEINDEX 100
     --#STATE OPERATIONAL
::= 7855


hpevtEepromInvalidCksm TRAP-TYPE
     ENTERPRISE hpIpfE0Events
     VARIABLES { hpIpfEvtDetailStr }
     DESCRIPTION
        "An invalid checksum was received when reading the FRUID EEPROM for the device named in the chassis code. If this is a single error, the fault lies with the named FRU. If there are many INVALID_CKSM entries in the Event Log, there is probably a problem with the I2C bus."

     --#SUMMARY "Invalid checksum from EEPROM"
     --#ARGUMENTS {}
     --#SEVERITY CRITICAL
     --#TIMEINDEX 100
     --#STATE OPERATIONAL
::= 7856


hpevtHbpbBoardPowerFault TRAP-TYPE
     ENTERPRISE hpIpfE0Events
     VARIABLES { hpIpfEvtDetailStr }
     DESCRIPTION
        " One or more of the System Backplane Power Boards is reporting a DC 
 Fault through the System Backplane Local Power Monitor.  The physical 
 location of the failing power board is in the Data Field of the event."

     --#SUMMARY "System Backplane Power Board Fault"
     --#ARGUMENTS {}
     --#SEVERITY WARNING
     --#TIMEINDEX 100
     --#STATE OPERATIONAL
::= 7858


hpevtHiobEepromRdFail TRAP-TYPE
     ENTERPRISE hpIpfE0Events
     VARIABLES { hpIpfEvtDetailStr }
     DESCRIPTION
        "An attempt to read the EEPROM (FRUID) on the IO Backplane Board failed."

     --#SUMMARY "Read of EEPROM failed"
     --#ARGUMENTS {}
     --#SEVERITY WARNING
     --#TIMEINDEX 100
     --#STATE OPERATIONAL
::= 7863


hpevtHiopbEepromRdFail TRAP-TYPE
     ENTERPRISE hpIpfE0Events
     VARIABLES { hpIpfEvtDetailStr }
     DESCRIPTION
        "An attempt to read the EEPROM (FRUID) on the IO Backplane Power Board failed."

     --#SUMMARY "Read of EEPROM failed"
     --#ARGUMENTS {}
     --#SEVERITY WARNING
     --#TIMEINDEX 100
     --#STATE OPERATIONAL
::= 7864


hpevtHiopbLpmFltRdFail TRAP-TYPE
     ENTERPRISE hpIpfE0Events
     VARIABLES { hpIpfEvtDetailStr }
     DESCRIPTION
        "An attempt to read the Local Power Monitor Fault register on the IO Backplane Power Board failed."

     --#SUMMARY "Read of LPM Fault failed"
     --#ARGUMENTS {}
     --#SEVERITY WARNING
     --#TIMEINDEX 100
     --#STATE OPERATIONAL
::= 7865


hpevtHiopbOvertemp TRAP-TYPE
     ENTERPRISE hpIpfE0Events
     VARIABLES { hpIpfEvtDetailStr }
     DESCRIPTION
        "The Local Power Monitor of the named IO Chassis is reporting a Power Brick overtemperature condition."

     --#SUMMARY "IO Power Board Overtemperature"
     --#ARGUMENTS {}
     --#SEVERITY CRITICAL
     --#TIMEINDEX 100
     --#STATE OPERATIONAL
::= 7866


hpevtHiopbPowerFault TRAP-TYPE
     ENTERPRISE hpIpfE0Events
     VARIABLES { hpIpfEvtDetailStr }
     DESCRIPTION
        "The Local Power Monitor on the named IO Chassis has reported a power fault condition."

     --#SUMMARY "IO Power Board Fault"
     --#ARGUMENTS {}
     --#SEVERITY CRITICAL
     --#TIMEINDEX 100
     --#STATE OPERATIONAL
::= 7867


hpevtHiopbVoltMrgnFail TRAP-TYPE
     ENTERPRISE hpIpfE0Events
     VARIABLES { hpIpfEvtDetailStr }
     DESCRIPTION
        "The Local Power Monitor on the named IO Power Board failed to properly margin the power as commanded."

     --#SUMMARY "Voltage Margin on IO Power Board failed"
     --#ARGUMENTS {}
     --#SEVERITY WARNING
     --#TIMEINDEX 100
     --#STATE OPERATIONAL
::= 7871


hpevtReadFruDataFail TRAP-TYPE
     ENTERPRISE hpIpfE0Events
     VARIABLES { hpIpfEvtDetailStr }
     DESCRIPTION
        "During command execution or as part of initialization, the data from a FRUID EEPROM failed to be read. This does not necessarily mean the FRU has failed, just that the FRUID can't be read.  

The data field is defined as follows:
   data field: 0xXXXXFFFFFFFFFFFF

Where XXXX is the specific FRU Handle of the failing FRUID.

The bits are defined as follows:
FRU handle
Reserved fields should be set to zero to be forward compatible with 
future FRU handle modifications

 Bits 15 - 12:  Cabinet number field
 Bits 11 -  9:  FRU family field
   0 - Utility
   1 - Misc
   2 - Power
   3 - Memory
   4 - Reserved
   5 - Reserved
   6 - Reserved
   7 - Reserved

 Bits  8 -  0:  Free format field based on FRU family field
   Utility family field
     Bits 8 - 6:  Utility type field
       0 - MP 
         Bits 5 - 0:  Reserved
       1 - SBCH
         Bits 5 - 0:  Reserved
       2 - UGUY
         Bits 5 - 0:  Reserved
       3 - CIO
         Bits 5 - 4:  Reserved
         Bits 3 - 2:  Master IO backplane number
         Bits 1 - 0:  IO bay number
       4 - PDH daughtercard
         Bits 5 - 3:  Reserved
         Bits 2 - 0:  Slot number
       5 - Reserved
         Bits 5 - 0:  Reserved
       6 - Reserved
         Bits 5 - 0:  Reserved
       7 - Reserved
         Bits 5 - 0:  Reserved

   Misc family field
     Bits 8 - 6:  Misc type field
       0 - Main backplane
         Bits 5 - 0:  Reserved
       1 - IO bay
         Bits 5 - 4:  Reserved
         Bits 3 - 2:  Master IO backplane number
         Bits 1 - 0:  IO bay number
       2 - Cell
         Bits 5 - 3:  Reserved
         Bits 2 - 0:  Slot number
       3 - Reserved
         Bits 5 - 0:  Reserved
       4 - Processor Module
         Bit 5:  Reserved
         Bits 4 - 2: Cell slot number
         Bits 1 - 0: Processor module number
       5 - Reserved
         Bits 5 - 0:  Reserved
       6 - Reserved
         Bits 5 - 0:  Reserved
       7 - Reserved
         Bits 5 - 0:  Reserved

   Power family field
     Bits 8 - 6:  Power type field
       0 - Main backplane power board
         Bits 5 - 2:  Reserved
         Bits 1 - 0:  Pwr bd number
       1 - IO bay power board
         Bits 5 - 4:  Reserved
         Bits 3 - 2:  Master IO BP number
         Bits 1 - 0:  IO bay number
       2 - Cell power board
         Bits 5 - 3:  Reserved
         Bits 2 - 0:  Slot number
       3 - Bay power supply
         Bits 5 - 3:  Reserved
         Bits 2 - 0:  Supply number
       4 - Processor module power pod
         Bit 5:  Reserved
         Bits 4 - 2:  Cell slot number
         Bits 1 - 0:  Processor module number
       5 - Reserved
         Bits 5 - 0:  Reserved
       6 - Reserved
         Bits 5 - 0:  Reserved
       7 - Reserved
         Bits 5 - 0:  Reserved

   Memory family field
     Bit  8:      Reserved
     Bits 7 - 5:  Slot number
     Bits 4 - 0:  DIMM number"

     --#SUMMARY "Failure to read data from a FRUID EEPROM"
     --#ARGUMENTS {}
     --#SEVERITY WARNING
     --#TIMEINDEX 100
     --#STATE OPERATIONAL
::= 7872


hpevtSbchEepromRdFail TRAP-TYPE
     ENTERPRISE hpIpfE0Events
     VARIABLES { hpIpfEvtDetailStr }
     DESCRIPTION
        "Either by command or as part of initialization, the data from a FRUID EEPROM failed a read command. This does not necessarily mean the FRU has failed, just that the FRUID data cannot be read."

     --#SUMMARY "Failure to read data from a SBCH FRUID EEPROM"
     --#ARGUMENTS {}
     --#SEVERITY WARNING
     --#TIMEINDEX 100
     --#STATE OPERATIONAL
::= 7873


hpevtUguyEepromRdFail TRAP-TYPE
     ENTERPRISE hpIpfE0Events
     VARIABLES { hpIpfEvtDetailStr }
     DESCRIPTION
        "Either by command or as part of initialization, the data from a FRUID EEPROM failed a read command. This does not necessarily mean the FRU has failed, just that the FRUID can't be read."

     --#SUMMARY "Failure to read data from a UGUY FRUID EEPROM"
     --#ARGUMENTS {}
     --#SEVERITY WARNING
     --#TIMEINDEX 100
     --#STATE OPERATIONAL
::= 7874


hpevtSysBkpEepromRdFail TRAP-TYPE
     ENTERPRISE hpIpfE0Events
     VARIABLES { hpIpfEvtDetailStr }
     DESCRIPTION
        "An attempt to read the EEPROM (FRUID) on the System Backplane failed"

     --#SUMMARY "Read EEPROM failed"
     --#ARGUMENTS {}
     --#SEVERITY WARNING
     --#TIMEINDEX 100
     --#STATE OPERATIONAL
::= 7875


hpevtSysBkpI2cRdFail TRAP-TYPE
     ENTERPRISE hpIpfE0Events
     VARIABLES { hpIpfEvtDetailStr }
     DESCRIPTION
        "A read command on the system backplane I2C bus failed."

     --#SUMMARY "Read command on System Backplane I2C bus failed"
     --#ARGUMENTS {}
     --#SEVERITY WARNING
     --#TIMEINDEX 100
     --#STATE OPERATIONAL
::= 7877


hpevtSysBkpI2cWrFail TRAP-TYPE
     ENTERPRISE hpIpfE0Events
     VARIABLES { hpIpfEvtDetailStr }
     DESCRIPTION
        "A write command on the system backplane I2C bus failed. The type of command that failed can be identified by the activity status field (last byte) of the encoded field. 
 
   B = RC Cable Configuration Register write 
   C = Backplane Voltage Margin Register write 
   9 = Flex circuit configuration register write"

     --#SUMMARY "Write command on System Backplane I2C bus failed"
     --#ARGUMENTS {}
     --#SEVERITY WARNING
     --#TIMEINDEX 100
     --#STATE OPERATIONAL
::= 7878


hpevtSysBkpPowerFault TRAP-TYPE
     ENTERPRISE hpIpfE0Events
     VARIABLES { hpIpfEvtDetailStr }
     DESCRIPTION
        "The Local Power Monitor on the named System Backplane has detected a power fault. The failing Backplane Power Board status is read from the Backplane LPM I2C interface register and the value is placed in the data field of the event (bits 15-8)."

     --#SUMMARY "Syatem Backplane Power Fault"
     --#ARGUMENTS {}
     --#SEVERITY CRITICAL
     --#TIMEINDEX 100
     --#STATE OPERATIONAL
::= 7879


hpevtSysBkpVoltMrgnFail TRAP-TYPE
     ENTERPRISE hpIpfE0Events
     VARIABLES { hpIpfEvtDetailStr }
     DESCRIPTION
        "Margining voltage to the System Backplane has failed."

     --#SUMMARY "System Backplane voltage margin failed"
     --#ARGUMENTS {}
     --#SEVERITY CRITICAL
     --#TIMEINDEX 100
     --#STATE OPERATIONAL
::= 7880


hpevtWriteFruDataFail TRAP-TYPE
     ENTERPRISE hpIpfE0Events
     VARIABLES { hpIpfEvtDetailStr }
     DESCRIPTION
        "An attempt to write data to the FRUID EEPROM by the MFG level MP command WF failed. The FRU handle of the failing FRUID is embedded in the two uppermost bytes of the data field."

     --#SUMMARY "Failure to write data to FRUID EEPROM"
     --#ARGUMENTS {}
     --#SEVERITY WARNING
     --#TIMEINDEX 100
     --#STATE OPERATIONAL
::= 7891


hpevtCpuFanFail TRAP-TYPE
     ENTERPRISE hpIpfE0Events
     VARIABLES { hpIpfEvtDetailStr }
     DESCRIPTION
        "The fan on a CPU is not operating in a manner that provides enough air flow to cool the processor"

     --#SUMMARY "CPU fan failed"
     --#ARGUMENTS {}
     --#SEVERITY CRITICAL
     --#TIMEINDEX 100
     --#STATE OPERATIONAL
::= 7892


hpevtCpuFanSlow TRAP-TYPE
     ENTERPRISE hpIpfE0Events
     VARIABLES { hpIpfEvtDetailStr }
     DESCRIPTION
        "The fan on a CPU is operating in a manner that provides enough air flow to cool the processor but is not at normal operation"

     --#SUMMARY "CPU fan failing"
     --#ARGUMENTS {}
     --#SEVERITY WARNING
     --#TIMEINDEX 100
     --#STATE OPERATIONAL
::= 7893


hpevtDnaFanFail TRAP-TYPE
     ENTERPRISE hpIpfE0Events
     VARIABLES { hpIpfEvtDetailStr }
     DESCRIPTION
        "The fan on a CC chip is not operating in a manner that provides enough air flow to cool the processor"

     --#SUMMARY "CC chip fan failed"
     --#ARGUMENTS {}
     --#SEVERITY CRITICAL
     --#TIMEINDEX 100
     --#STATE OPERATIONAL
::= 7894


hpevtDnaFanSlow TRAP-TYPE
     ENTERPRISE hpIpfE0Events
     VARIABLES { hpIpfEvtDetailStr }
     DESCRIPTION
        "The fan on a CC chip is operating in a manner that provides enough air flow to cool the processor but is not at normal operation"

     --#SUMMARY "CC chip fan failing"
     --#ARGUMENTS {}
     --#SEVERITY WARNING
     --#TIMEINDEX 100
     --#STATE OPERATIONAL
::= 7895


hpevtPdhcToSysfwRevMismtch TRAP-TYPE
     ENTERPRISE hpIpfE0Events
     VARIABLES { hpIpfEvtDetailStr }
     DESCRIPTION
        "System FW and the PDHC have incompatible shared memory interface revisions. 
 
Data byte 0 is the PDHC's supported ICM revision number. 
Data byte 1 is System FW's supported ICM revision number."

     --#SUMMARY "System FW and the PDHC have incompatible shared memory interface revisions"
     --#ARGUMENTS {}
     --#SEVERITY CRITICAL
     --#TIMEINDEX 100
     --#STATE OPERATIONAL
::= 7896


hpevtPdhCtrlrFwMismatch TRAP-TYPE
     ENTERPRISE hpIpfE0Events
     VARIABLES { hpIpfEvtDetailStr }
     DESCRIPTION
        "The MP checked the FW revision of the PDHC identified in the physical location data field and discovered that it did not recognize the revision as one that it has been qualed with. This is an unsupported configuration."

     --#SUMMARY "PDH Controller firmware version is not supported with this version of MP FW"
     --#ARGUMENTS {}
     --#SEVERITY CRITICAL
     --#TIMEINDEX 100
     --#STATE OPERATIONAL
::= 7902


hpevtCellPowerFault TRAP-TYPE
     ENTERPRISE hpIpfE0Events
     VARIABLES { hpIpfEvtDetailStr }
     DESCRIPTION
        "The local Power Monitor is reporting a fault with the named Cell Power Board.
The data field of this event can be decoded as follows where a bit set in any of the status fields indicates a fault:
data byte 0: (power_good << 1) | (power_fault)
data byte 1: Cell Power Board converters status
    bits[0:2] - memory power bricks 0-2 status
    bits[3:5] - power i/f bus bricks 0-2 status
    bits[6:7] - JAB core power bricks 0-1 status
data byte 2: Cell converters status
    bit 0 - clock power status
    bit 1 - cache power status
    bit 2 - link power status
    bit 3 - CC core power status
    bit 4 - FSB power status
    bit 5 - 48-V status
data byte 3: CPU module converters status
    bit 0 - CPU module 0 core power status
    bit 2 - CPU module 1 core power status
    bit 4 - CPU module 2 core power status
    bit 6 - CPU module 3 core power status"

     --#SUMMARY "Power fault on cell board"
     --#ARGUMENTS {}
     --#SEVERITY CRITICAL
     --#TIMEINDEX 100
     --#STATE OPERATIONAL
::= 7903


hpevtCpuInitNodeError TRAP-TYPE
     ENTERPRISE hpIpfE0Events
     VARIABLES { hpIpfEvtDetailStr }
     DESCRIPTION
        "The CPU node retuned an error when calling its initialize node function.  The specific status is displayed in the data field."

     --#SUMMARY "The CPU Node reported a problem initializing its node in the device tree"
     --#ARGUMENTS {}
     --#SEVERITY WARNING
     --#TIMEINDEX 100
     --#STATE OPERATIONAL
::= 7938


hpevtCpuExecuteCmdError TRAP-TYPE
     ENTERPRISE hpIpfE0Events
     VARIABLES { hpIpfEvtDetailStr }
     DESCRIPTION
        "ExecuteCommand issues commands that execute on remote CPUs via IPI interrupts.  If the command failed to execute, this event is printed and the data field contains the status."

     --#SUMMARY "The ExecuteCommand function failed on a CPU."
     --#ARGUMENTS {}
     --#SEVERITY WARNING
     --#TIMEINDEX 100
     --#STATE OPERATIONAL
::= 7939


hpevtCpuCmdStateInvalid TRAP-TYPE
     ENTERPRISE hpIpfE0Events
     VARIABLES { hpIpfEvtDetailStr }
     DESCRIPTION
        "A remote CPU is in a state where it cannot receive and execute a new command.  The current status of the CPU is provided in the data field."

     --#SUMMARY "A remote CPU is not prepared to receive a command"
     --#ARGUMENTS {}
     --#SEVERITY WARNING
     --#TIMEINDEX 100
     --#STATE OPERATIONAL
::= 7940


hpevtCpuPalProcError TRAP-TYPE
     ENTERPRISE hpIpfE0Events
     VARIABLES { hpIpfEvtDetailStr }
     DESCRIPTION
        "An error was encountered when executing a PAL_PROC.  This code will be emitted in pairs.  The Proc INDEX will be in the data of the first chassis code.  The status is in the second data field."

     --#SUMMARY "An error was encountered when executing a PAL_PROC"
     --#ARGUMENTS {}
     --#SEVERITY WARNING
     --#TIMEINDEX 100
     --#STATE OPERATIONAL
::= 7948


hpevtBootCpuLoadingError TRAP-TYPE
     ENTERPRISE hpIpfE0Events
     VARIABLES { hpIpfEvtDetailStr }
     DESCRIPTION
        "CPUs not loaded in correct order.  Correct loading order is CPU 0, 1, 2, 3."

     --#SUMMARY "CPUs loaded in wrong order"
     --#ARGUMENTS {}
     --#SEVERITY CRITICAL
     --#TIMEINDEX 100
     --#STATE OPERATIONAL
::= 7953


hpevtXbcPersistantError TRAP-TYPE
     ENTERPRISE hpIpfE0Events
     VARIABLES { hpIpfEvtDetailStr }
     DESCRIPTION
        "The XBC logged a SBE or LPE after they should have been cleared.  Either the clear failed, or a new error was logged immediately. 
Data field:  XBC number (32:43), port number (44:55), port status information (0:31)"

     --#SUMMARY "The XBC SBE and LPE errors were not cleared properly"
     --#ARGUMENTS {}
     --#SEVERITY CRITICAL
     --#TIMEINDEX 100
     --#STATE OPERATIONAL
::= 7963


hpevtXbcLinkTestError TRAP-TYPE
     ENTERPRISE hpIpfE0Events
     VARIABLES { hpIpfEvtDetailStr }
     DESCRIPTION
        "The CC to XBC Link pattern test failed.  
 
Data Field: This event will be emitted three times 
                   1st event: XBC number (32:43), port number (44:55) 
                   2nd event: expected pattern (0:63) 
                   3rd event: actual data read (0:63)"

     --#SUMMARY "The CC to XBC link pattern test failed."
     --#ARGUMENTS {}
     --#SEVERITY CRITICAL
     --#TIMEINDEX 100
     --#STATE OPERATIONAL
::= 7964


hpevtPltfrmStorageReadErr TRAP-TYPE
     ENTERPRISE hpIpfE0Events
     VARIABLES { hpIpfEvtDetailStr }
     DESCRIPTION
        "System firmware was unable to complete a platform storage read command from the utilities system.  The exact status printed in the data field."

     --#SUMMARY "Error Reading a platform storage variable from the PDHC/MP"
     --#ARGUMENTS {}
     --#SEVERITY CRITICAL
     --#TIMEINDEX 100
     --#STATE OPERATIONAL
::= 7965


hpevtPltfrmStorageWriteErr TRAP-TYPE
     ENTERPRISE hpIpfE0Events
     VARIABLES { hpIpfEvtDetailStr }
     DESCRIPTION
        "System firmware was unable to complete a platform storage write command.  The actual status is returned in the data field."

     --#SUMMARY "An error was returned on a Platform Storage Write Command to the PDHC/MP"
     --#ARGUMENTS {}
     --#SEVERITY CRITICAL
     --#TIMEINDEX 100
     --#STATE OPERATIONAL
::= 7966


hpevtTreeNodeErrorSequencer TRAP-TYPE
     ENTERPRISE hpIpfE0Events
     VARIABLES { hpIpfEvtDetailStr }
     DESCRIPTION
        "The Sequencer was unable to find the tree node it needed to complete an operation.  The tree node is in the ascii in the data field."

     --#SUMMARY "The Sequencer was unable to find/use a needed tree node"
     --#ARGUMENTS {}
     --#SEVERITY CRITICAL
     --#TIMEINDEX 100
     --#STATE OPERATIONAL
::= 7973


hpevtPartitionVariableError TRAP-TYPE
     ENTERPRISE hpIpfE0Events
     VARIABLES { hpIpfEvtDetailStr }
     DESCRIPTION
        "System firmware atempted to read a partition variable from the GSP and store it in options.  An error was encountered during this process.  The data field contains the partition variable element ID that was being processed."

     --#SUMMARY "Firmware encountered an error in processing the partition variables"
     --#ARGUMENTS {}
     --#SEVERITY CRITICAL
     --#TIMEINDEX 100
     --#STATE OPERATIONAL
::= 7974


hpevtCellRedundtPowerFault TRAP-TYPE
     ENTERPRISE hpIpfE0Events
     VARIABLES { hpIpfEvtDetailStr }
     DESCRIPTION
        "One or more power converters on the Cell or Cell Power Board has reported a fault. However, because of redundancy in the power system, the power to the Cell is still good. The data field contains detailed power fault location information that is specific to each platform."

     --#SUMMARY "A non-critical cell power fault has occurred"
     --#ARGUMENTS {}
     --#SEVERITY CRITICAL
     --#TIMEINDEX 100
     --#STATE OPERATIONAL
::= 7975


hpevtPalProcConfigIncompatible TRAP-TYPE
     ENTERPRISE hpIpfE0Events
     VARIABLES { hpIpfEvtDetailStr }
     DESCRIPTION
        "CPUProcConfigValue setting in options as been compared with what is reported by PAL as settable and CPUProcConfigValue is specifying at least one bit that is not supported by this version of PAL using the Get Processor Dependent Features. This chassis code is emmitted in pairs, the first data field contains the PAL expected values; the second data field contains the requested setting from options."

     --#SUMMARY "CPUProcConfigValue in /options is not compatible with the current PAL/CPU"
     --#ARGUMENTS {}
     --#SEVERITY CRITICAL
     --#TIMEINDEX 100
     --#STATE OPERATIONAL
::= 8009


hpevtPalGetProcFeaturesFailed TRAP-TYPE
     ENTERPRISE hpIpfE0Events
     VARIABLES { hpIpfEvtDetailStr }
     DESCRIPTION
        "System firmware was unable to successfully issue the PAL_GET_PROC_FEATURES PAL proc.  The data field is unused"

     --#SUMMARY "Firmware was unable to determine the Processor Dependent Features"
     --#ARGUMENTS {}
     --#SEVERITY WARNING
     --#TIMEINDEX 100
     --#STATE OPERATIONAL
::= 8010


hpevtPdhcCriticalDebug TRAP-TYPE
     ENTERPRISE hpIpfE0Events
     VARIABLES { hpIpfEvtDetailStr }
     DESCRIPTION
        "This event is a tool to aid in the debugging and testing of firmware."

     --#SUMMARY "Data field contains data meant for firmware debug only."
     --#ARGUMENTS {}
     --#SEVERITY CRITICAL
     --#TIMEINDEX 100
     --#STATE OPERATIONAL
::= 8127


hpevtCluUndefinedCase TRAP-TYPE
     ENTERPRISE hpIpfE0Events
     VARIABLES { hpIpfEvtDetailStr }
     DESCRIPTION
        "The CLU has encountered an undefined case in its control flow."

     --#SUMMARY "The CLU has encountered an undefined case"
     --#ARGUMENTS {}
     --#SEVERITY CRITICAL
     --#TIMEINDEX 100
     --#STATE OPERATIONAL
::= 8128


hpevtCellVoltageMarginUnkn TRAP-TYPE
     ENTERPRISE hpIpfE0Events
     VARIABLES { hpIpfEvtDetailStr }
     DESCRIPTION
        "The Cell voltage margin settings do not match the Normal, +5%, or -5% values."

     --#SUMMARY "An unknown Cell voltage margin has been detected."
     --#ARGUMENTS {}
     --#SEVERITY WARNING
     --#TIMEINDEX 100
     --#STATE OPERATIONAL
::= 8130


hpevtPdhcAssertionFailed TRAP-TYPE
     ENTERPRISE hpIpfE0Events
     VARIABLES { hpIpfEvtDetailStr }
     DESCRIPTION
        "For debug purposes, many assumptions made by the PDHC developer(s) are checked at run-time. If this event log is seen, it indicates that the hardware or software is in an unknown state. For developer debug purposes, the data field describes where in the code that the error was detected. 
Data Bytes[0-1]: The line number within the source code file where the error was detected. 
Data Bytes[2-7]: The first 6 characters of the source code file name."

     --#SUMMARY "The run-time verification of a programming assumption has failed."
     --#ARGUMENTS {}
     --#SEVERITY WARNING
     --#TIMEINDEX 100
     --#STATE OPERATIONAL
::= 8131


hpevtPdhcFirmwareUnknownErr TRAP-TYPE
     ENTERPRISE hpIpfE0Events
     VARIABLES { hpIpfEvtDetailStr }
     DESCRIPTION
        "An unknown error has been detected by the PDHC firmware. For developer debug purposes, the data field describes where in the code that the error was detected. 
Data Bytes[0-1]: The line number within the source code file where the error was detected. 
Data Bytes[2-7]: The first 6 characters of the source code file name."

     --#SUMMARY "An unknown error has been detected by the PDHC firmware."
     --#ARGUMENTS {}
     --#SEVERITY WARNING
     --#TIMEINDEX 100
     --#STATE OPERATIONAL
::= 8132


hpevtPdhcI2cWriteFailed TRAP-TYPE
     ENTERPRISE hpIpfE0Events
     VARIABLES { hpIpfEvtDetailStr }
     DESCRIPTION
        "An attempt to write to a device on the PDHC's I2C bus has failed. The devices on the I2C bus are the Cell's FRU EEPROM, the Cell Power Board's FRU EEPROM, the voltage margining D-to-A converters, and, if they are accessible, the CPU Module Power Pods' FRU EEPROMs. The Data field information contains information that can identify the exact device that has failed. Refer to the Cell ERS for a mapping of I2C device addresses to devices. 
Data Bytes[0-1]: Reserved 
Data Bytes[2-3]: I2C Device Address 
Data Bytes[4-5]: Starting Word Address 
Data Bytes[6-7]: Size of attempted access (in bytes)."

     --#SUMMARY "An attempt to write to a device on the PDHCs I2C bus has failed."
     --#ARGUMENTS {}
     --#SEVERITY WARNING
     --#TIMEINDEX 100
     --#STATE OPERATIONAL
::= 8133


hpevtPdhcI2cReadFailed TRAP-TYPE
     ENTERPRISE hpIpfE0Events
     VARIABLES { hpIpfEvtDetailStr }
     DESCRIPTION
        "An attempt to read from a device on the PDHC's I2C bus has failed. The devices on the I2C bus are the Cell's FRU EEPROM, the Cell Power Board's FRU EEPROM, the voltage margining D-to-A converters, and, if they are accessible, the CPU Module Power Pods' FRU EEPROMs. The Data field information contains information that can identify the exact device that has failed. Refer to the Cell ERS for a mapping of I2C device addresses to devices. 
Data Bytes[0-1]: Reserved 
Data Bytes[2-3]: I2C Device Address 
Data Bytes[4-5]: Starting Word Address 
Data Bytes[6-7]: Size of attempted access (in bytes)."

     --#SUMMARY "An attempt to read from a device on the PDHC's I2C bus has failed."
     --#ARGUMENTS {}
     --#SEVERITY WARNING
     --#TIMEINDEX 100
     --#STATE OPERATIONAL
::= 8134


hpevtPdhcSmbusWriteFailed TRAP-TYPE
     ENTERPRISE hpIpfE0Events
     VARIABLES { hpIpfEvtDetailStr }
     DESCRIPTION
        "An attempt to write to a device on the PDHC's SM bus has failed. The devices on the SM bus are the CPU modules' FRU EEPROMs, the CPU modules' Processor Information ROMs, and the CPU modules' thermal sensors. The Data field information contains information that can identify the exact device that has failed. Refer to the Cell ERS for a mapping of SM Bus device addresses to devices. 
Data Bytes[0-1]: Reserved 
Data Bytes[2-3]: SM bus Device Address 
Data Bytes[4-5]: Starting Word Address 
Data Bytes[6-7]: Size of attempted access (in bytes)."

     --#SUMMARY "An attempt to write to a device on the PDHC's SM bus has failed."
     --#ARGUMENTS {}
     --#SEVERITY WARNING
     --#TIMEINDEX 100
     --#STATE OPERATIONAL
::= 8135


hpevtPdhcSmbusReadFailed TRAP-TYPE
     ENTERPRISE hpIpfE0Events
     VARIABLES { hpIpfEvtDetailStr }
     DESCRIPTION
        "An attempt to read from a device on the PDHC's SM bus has failed. The devices on the SM bus are the CPU modules' FRU EEPROMs, the CPU modules' Processor Information ROMs, and the CPU modules' thermal sensors. The Data field information contains information that can identify the exact device that has failed. Refer to the Cell ERS for a mapping of SM Bus device addresses to devices. 
Data Bytes[0-1]: Reserved 
Data Bytes[2-3]: SM bus Device Address 
Data Bytes[4-5]: Starting Word Address 
Data Bytes[6-7]: Size of attempted access (in bytes)."

     --#SUMMARY "An attempt to read from a device on the PDHC's SM bus has failed."
     --#ARGUMENTS {}
     --#SEVERITY WARNING
     --#TIMEINDEX 100
     --#STATE OPERATIONAL
::= 8136


hpevtFrequencyProgramFailed TRAP-TYPE
     ENTERPRISE hpIpfE0Events
     VARIABLES { hpIpfEvtDetailStr }
     DESCRIPTION
        "The PDHC did not read valid frequency information from the CPU modules' or Cell's FRU EEPROMs, or the frequency registers would not update properly. Following this event, the Cell will not boot until the problem is corrected and Cell Power has been turned off, then on again, using the PE command."

     --#SUMMARY "Cell boot has been disabled due to a failure setting the frequency registers."
     --#ARGUMENTS {}
     --#SEVERITY CRITICAL
     --#TIMEINDEX 100
     --#STATE OPERATIONAL
::= 8137


hpevtSysFwFlashUpdateError TRAP-TYPE
     ENTERPRISE hpIpfE0Events
     VARIABLES { hpIpfEvtDetailStr }
     DESCRIPTION
        "An error has occurred while updating System FW. More details about the update failure may be available as displayed by the Firmware Update Utility (FWUU)."

     --#SUMMARY "An error has occurred while updating System FW."
     --#ARGUMENTS {}
     --#SEVERITY WARNING
     --#TIMEINDEX 100
     --#STATE OPERATIONAL
::= 8138


hpevtPdhcUnexpectedReset TRAP-TYPE
     ENTERPRISE hpIpfE0Events
     VARIABLES { hpIpfEvtDetailStr }
     DESCRIPTION
        "The PDHC firmware was reset for some unknown reason."

     --#SUMMARY "The PDHC firmware was reset for some unknown reason."
     --#ARGUMENTS {}
     --#SEVERITY WARNING
     --#TIMEINDEX 100
     --#STATE OPERATIONAL
::= 8139


hpevtCpuTmpSensorSetupFail TRAP-TYPE
     ENTERPRISE hpIpfE0Events
     VARIABLES { hpIpfEvtDetailStr }
     DESCRIPTION
        "A hardware fault prevented the PDHC from configuring the thermal sensor(s) on one or more of the CPU modules. Following detection of this fault condition, the Cell will be prevented from booting until the Cell is powered 'off', then 'on', using the PE command."

     --#SUMMARY "Cell boot has been disabled because setup of a CPU thermal sensor failed."
     --#ARGUMENTS {}
     --#SEVERITY CRITICAL
     --#TIMEINDEX 100
     --#STATE OPERATIONAL
::= 8140


hpevtCpuModuleThermalert TRAP-TYPE
     ENTERPRISE hpIpfE0Events
     VARIABLES { hpIpfEvtDetailStr }
     DESCRIPTION
        "A CPU module's temperature has exceed the high temperature threshold. As a result of this event, an irrevocable 2 minute timer will begin. At the end of 2 minutes, the offending CPU module will be powered off by the Cell hardware. The Cell must be powered off then on using the MP's PE command before the CPU module will be powered again."

     --#SUMMARY "A CPU module has reported overtemp, so will be powered off in 1 minute."
     --#ARGUMENTS {}
     --#SEVERITY CRITICAL
     --#TIMEINDEX 100
     --#STATE OPERATIONAL
::= 8141


hpevtPdhcFlashUpdateError TRAP-TYPE
     ENTERPRISE hpIpfE0Events
     VARIABLES { hpIpfEvtDetailStr }
     DESCRIPTION
        "An error occurred while updating the PDHC firmware. More specific details of the update error may be displayed by the Firmware Update utility running on the MP."

     --#SUMMARY "An error occurred while updating the PDHC firmware."
     --#ARGUMENTS {}
     --#SEVERITY WARNING
     --#TIMEINDEX 100
     --#STATE OPERATIONAL
::= 8143


hpevtCellTypMismatchWSysfw TRAP-TYPE
     ENTERPRISE hpIpfE0Events
     VARIABLES { hpIpfEvtDetailStr }
     DESCRIPTION
        "The cell type (IPF or PA) does not match System FW type. The cell type is detected based on information stored in CPU modules' FRUID EEPROMs. The System FW type is determined based on data that is embedded in the System FW ROM image. This is checked each time Cell power transitions from off to on, and each time the System FW is updated. Following the detection of this mismatch, the Cell will not be allowed to boot until the problem has been resolved."

     --#SUMMARY "Boot is disabled because the cell type does not match the System FW ROM type."
     --#ARGUMENTS {}
     --#SEVERITY CRITICAL
     --#TIMEINDEX 100
     --#STATE OPERATIONAL
::= 8147


hpevtPdhcPdhArbiterTimeout TRAP-TYPE
     ENTERPRISE hpIpfE0Events
     VARIABLES { hpIpfEvtDetailStr }
     DESCRIPTION
        "This event is emitted after the PDHC has waited longer than a maximum expected time for the PDH arbiter to grant it control of the PDH bus. The PDHC will continue waiting for contol of the PDH bus until the arbiter grants it control, or the Cell is powered off using the MP's PE command. While waiting for the PDH bus, the PDHC will NOT perform its normal duties such as monitoring the Cell status, and passing messages from the system to the MP, and the PDHC heartbeat will not blink."

     --#SUMMARY "The PDHC has waited an abnormally long time for PDH bus access."
     --#ARGUMENTS {}
     --#SEVERITY WARNING
     --#TIMEINDEX 100
     --#STATE OPERATIONAL
::= 8149


hpevtPdhcGetSm4Timeout TRAP-TYPE
     ENTERPRISE hpIpfE0Events
     VARIABLES { hpIpfEvtDetailStr }
     DESCRIPTION
        "This event is emitted after the PDHC has waited longer than a maximum expected time to obtain control of the PDH bus semaphore. The PDHC will continue waiting for contol of the PDH bus semaphore until System FW relinquishes control of the semaphore, or the Cell is powered off using the MP's PE command. While waiting for the PDH bus semaphore, the PDHC will NOT perform its normal duties such as monitoring the Cell status, and passing messages from the system to the MP, and the PDHC heartbeat will not blink. 
 
The data field contains debug data that may be useful for developers. 
Data_byte[0] = last value read from PDHC's address for the microSemaphore register. 
Data_byte[1] = boolean indicator (1=set,0=not_set) of whether the PDHC's flag is set. 
Data_byte[2] = boolean indicator (1=set,0=not_set) of whether the System FW's flag is set."

     --#SUMMARY "The PDHC has waited an abnormally long time to obtain the PDH semaphore."
     --#ARGUMENTS {}
     --#SEVERITY WARNING
     --#TIMEINDEX 100
     --#STATE OPERATIONAL
::= 8151


hpevtIpmiBmc2hostMsgFailure TRAP-TYPE
     ENTERPRISE hpIpfE0Events
     VARIABLES { hpIpfEvtDetailStr }
     DESCRIPTION
        "This event indicates that an error occurred while transmitting an IPMI message in the BMC2HOST direction. The data field contains more detailed information about the source of the error. Data Bytes 0 & 1 form a 16-bit IPMI error indicator that has the following values and meanings: 
1 - IPMI_HOST_BUSY_TIMEOUT - The PDHC could not put a message in the BMC2HOST hardware message queue for over 10 seconds, so the pending message(s) were dropped. 
2 - IPMI_INVALID_MSG_SIZE - The MP sent an IPMI message response that has an embedded size indicator that is less than 4 bytes or greater than the size of the message data. The poorly formed message response will be dropped. 
3 - IPMI_BMC2HOST_Q_FULL - The BMC2HOST message queue in the PDHC is full, so a message response from the MP has been dropped."

     --#SUMMARY "An error occurred while transmitting an IPMI message in the BMC2HOST direction."
     --#ARGUMENTS {}
     --#SEVERITY WARNING
     --#TIMEINDEX 100
     --#STATE OPERATIONAL
::= 8153


hpevtEfiDebugLevelTokenErr TRAP-TYPE
     ENTERPRISE hpIpfE0Events
     VARIABLES { hpIpfEvtDetailStr }
     DESCRIPTION
        "EFI was unable to read the initial debug level from the BMC token.   EFI will continue with an unknown value for the debug level. 
Data Field:  Return status from internal EFI function."

     --#SUMMARY "EFI unable to read initial debug level from the BMC"
     --#ARGUMENTS {}
     --#SEVERITY WARNING
     --#TIMEINDEX 100
     --#STATE OPERATIONAL
::= 8154


hpevtXbcPortNotLandmined TRAP-TYPE
     ENTERPRISE hpIpfE0Events
     VARIABLES { hpIpfEvtDetailStr }
     DESCRIPTION
        "A XBC port was unexpectedly found to not be landmined.  The data field consists of the XBC number (32:43) and the port number (44:55)."

     --#SUMMARY "A XBC port was unexpectedly found to not be landmined."
     --#ARGUMENTS {}
     --#SEVERITY CRITICAL
     --#TIMEINDEX 100
     --#STATE OPERATIONAL
::= 8156


hpevtFabricValidateError TRAP-TYPE
     ENTERPRISE hpIpfE0Events
     VARIABLES { hpIpfEvtDetailStr }
     DESCRIPTION
        "The number of landmined XBC ports was not within the allowable range.  There is a minimum number of landmined ports because some ports are always unused.  There is a maximum number of landmined ports because there is a limit to the number of broken links allowed in a system.  The data field shows the number of landmined ports found"

     --#SUMMARY "An invalid number of XBC ports were landmined in the system."
     --#ARGUMENTS {}
     --#SEVERITY CRITICAL
     --#TIMEINDEX 100
     --#STATE OPERATIONAL
::= 8159


hpevtFabricISRInvalidBkp TRAP-TYPE
     ENTERPRISE hpIpfE0Events
     VARIABLES { hpIpfEvtDetailStr }
     DESCRIPTION
        "Data field contains the backplane type found.  During Intra SKD Routing, the backplane type detected was either a Medel backplane or was unrecognized.  The backplane could therefore not be routed.  This is a firmware sanity check.  Data Field: system type"

     --#SUMMARY "The backplane was not recognized as one that contains fabric"
     --#ARGUMENTS {}
     --#SEVERITY CRITICAL
     --#TIMEINDEX 100
     --#STATE OPERATIONAL
::= 8184


hpevtFabricXinWrZeroErrMaskError TRAP-TYPE
     ENTERPRISE hpIpfE0Events
     VARIABLES { hpIpfEvtDetailStr }
     DESCRIPTION
        "Prior to initializing the CC to XBC link, the XIN error mask should be zeroed out to prevent spurious errors from interferring with the link initialization.  This write to zero out the error mask failed.  Data Field: (cell << 56) | return status"

     --#SUMMARY "Writing the XIN Error Mask Register to zero failed"
     --#ARGUMENTS {}
     --#SEVERITY WARNING
     --#TIMEINDEX 100
     --#STATE OPERATIONAL
::= 8186


hpevtFabricCcPriModeRegRdStatus TRAP-TYPE
     ENTERPRISE hpIpfE0Events
     VARIABLES { hpIpfEvtDetailStr }
     DESCRIPTION
        "The Coherency Controller's (CC) XIN link did not initialize properly.  The data field contains the return status from an attempted read of the CC Primary Error Mode CSR.  (0 = SUCCESS)"

     --#SUMMARY "Dumping error info. Read status of the Primary Mode Register"
     --#ARGUMENTS {}
     --#SEVERITY CRITICAL
     --#TIMEINDEX 100
     --#STATE OPERATIONAL
::= 8187


hpevtFabricCcPriModeRegRdData TRAP-TYPE
     ENTERPRISE hpIpfE0Events
     VARIABLES { hpIpfEvtDetailStr }
     DESCRIPTION
        "The Coherency Controller's (CC) XIN link did not initialize properly.  The data field contains the data read from the CC Primary Error Mode CSR."

     --#SUMMARY "Data read from the CC Primary Mode CSR"
     --#ARGUMENTS {}
     --#SEVERITY CRITICAL
     --#TIMEINDEX 100
     --#STATE OPERATIONAL
::= 8188


hpevtFabricCcErrMaskRegRdStatus TRAP-TYPE
     ENTERPRISE hpIpfE0Events
     VARIABLES { hpIpfEvtDetailStr }
     DESCRIPTION
        "The Coherency Controller's (CC) XIN link did not initialize properly.  The data field contains the return status from an attempted read of the CC Primary Error Mode CSR.  (0 = SUCCESS)"

     --#SUMMARY "Dumping error info. Read status of the CC Error Mask Register"
     --#ARGUMENTS {}
     --#SEVERITY CRITICAL
     --#TIMEINDEX 100
     --#STATE OPERATIONAL
::= 8189


hpevtFabricCcErrMaskRegRdData TRAP-TYPE
     ENTERPRISE hpIpfE0Events
     VARIABLES { hpIpfEvtDetailStr }
     DESCRIPTION
        "The Coherency Controller's (CC) XIN link did not initialize properly.  The data field contains the data read from the CC Error Mask CSR."

     --#SUMMARY "Data read from the CC Error Mask CSR"
     --#ARGUMENTS {}
     --#SEVERITY CRITICAL
     --#TIMEINDEX 100
     --#STATE OPERATIONAL
::= 8190


hpevtFabricXingNeighborPortBad TRAP-TYPE
     ENTERPRISE hpIpfE0Events
     VARIABLES { hpIpfEvtDetailStr }
     DESCRIPTION
        "The neighbor's port connected to the link being crossed is not routable.  This was the first attempt to cross the link, PDC will now look for another link it can cross.  DATA: (xbcNum << 32 ) | (port << 44)"

     --#SUMMARY "The link could not be crossed upon first attempt"
     --#ARGUMENTS {}
     --#SEVERITY WARNING
     --#TIMEINDEX 100
     --#STATE OPERATIONAL
::= 8194


hpevtFabricISRRdFwdProgErr TRAP-TYPE
     ENTERPRISE hpIpfE0Events
     VARIABLES { hpIpfEvtDetailStr }
     DESCRIPTION
        "Fabric read error.  Data field: (XBC number << 32 | return status)"

     --#SUMMARY "Failed reading an XBC forward progress register"
     --#ARGUMENTS {}
     --#SEVERITY CRITICAL
     --#TIMEINDEX 100
     --#STATE OPERATIONAL
::= 8195


hpevtFabricGetNeighborMaxLinksBroken TRAP-TYPE
     ENTERPRISE hpIpfE0Events
     VARIABLES { hpIpfEvtDetailStr }
     DESCRIPTION
        "Too many crossbar links are broken.  Cell cannot boot, halting.  Data field: XBC number << 32"

     --#SUMMARY "Could not find an adjacent XBC due to broken fabric links"
     --#ARGUMENTS {}
     --#SEVERITY CRITICAL
     --#TIMEINDEX 100
     --#STATE OPERATIONAL
::= 8198


hpevtPmAssertionFailed TRAP-TYPE
     ENTERPRISE hpIpfE0Events
     VARIABLES { hpIpfEvtDetailStr }
     DESCRIPTION
        "For debug purposes, many assumptions made by the PM developer(s) are checked at run-time. If this event log is seen, it will either indicate that the hardware is in a unknown state that is not handled by the PM, or that a programming bug has been found. For developer debug purposes, the data field describes where in the code that the error was detected. 
Data Bytes[0-1]: The line number within the source code file where the error was detected. 
Data Bytes[2-7]: The first 6 characters of the source code file name."

     --#SUMMARY "The run-time verification of a programming assumption has failed."
     --#ARGUMENTS {}
     --#SEVERITY WARNING
     --#TIMEINDEX 100
     --#STATE OPERATIONAL
::= 8199


hpevtPmFirmwareUnknownErr TRAP-TYPE
     ENTERPRISE hpIpfE0Events
     VARIABLES { hpIpfEvtDetailStr }
     DESCRIPTION
        "An unknown error has been detected by the PM firmware. For developer debug purposes, the data field describes where in the code that the error was detected. 
Data Bytes[0-1]: The line number within the source code file where the error was detected. 
Data Bytes[2-7]: The first 6 characters of the source code file name."

     --#SUMMARY "An unknown error has been detected by the PDHC firmware."
     --#ARGUMENTS {}
     --#SEVERITY WARNING
     --#TIMEINDEX 100
     --#STATE OPERATIONAL
::= 8200


hpevtPmCriticalDebug TRAP-TYPE
     ENTERPRISE hpIpfE0Events
     VARIABLES { hpIpfEvtDetailStr }
     DESCRIPTION
        "This event is a tool to aid in the debugging and testing of firmware."

     --#SUMMARY "Data field contains data meant for firmware debug only."
     --#ARGUMENTS {}
     --#SEVERITY CRITICAL
     --#TIMEINDEX 100
     --#STATE OPERATIONAL
::= 8202


hpevtFabricLinkCorErrTestFailure TRAP-TYPE
     ENTERPRISE hpIpfE0Events
     VARIABLES { hpIpfEvtDetailStr }
     DESCRIPTION
        "Failed link testing to ensure that SBE and LPE errors are detected properly by the XBC.  The XBC did not detect any errors.  Data field indicates the return status: (1 = err detected, 0 = no err detected, -1 = XBC accesses failed)"

     --#SUMMARY "Testing of correctable errors injected from the CC has failed"
     --#ARGUMENTS {}
     --#SEVERITY WARNING
     --#TIMEINDEX 100
     --#STATE OPERATIONAL
::= 8205


hpevtInvalidCabinetNumber TRAP-TYPE
     ENTERPRISE hpIpfE0Events
     VARIABLES { hpIpfEvtDetailStr }
     DESCRIPTION
        "The data field contains the cabinet number that is invalid"

     --#SUMMARY "A cabinet has been configured using an invalid cabinet number"
     --#ARGUMENTS {}
     --#SEVERITY CRITICAL
     --#TIMEINDEX 100
     --#STATE OPERATIONAL
::= 8206


hpevtPdIncompatibleFwRevs TRAP-TYPE
     ENTERPRISE hpIpfE0Events
     VARIABLES { hpIpfEvtDetailStr }
     DESCRIPTION
        "The cell indicated in the data field is at a different firmware revision than the reporting cell.  This is determined by evaluating the checksums of the 2 rom images."

     --#SUMMARY "Cells trying to join a PD are at incompatible firmware revisions"
     --#ARGUMENTS {}
     --#SEVERITY CRITICAL
     --#TIMEINDEX 100
     --#STATE OPERATIONAL
::= 8207


hpevtPmI2cWriteFailed TRAP-TYPE
     ENTERPRISE hpIpfE0Events
     VARIABLES { hpIpfEvtDetailStr }
     DESCRIPTION
        "An attempt to write to a device on the PM's I2C bus has failed.  
 
The Data field contains information that can identify the exact device that has failed. Refer to the UGUY ERS for a mapping of I2C device addresses to devices. 
Data Bytes[0-1]: Reserved 
Data Bytes[2-3]: I2C Device Address 
Data Bytes[4-5]: Starting Word Address 
Data Bytes[6-7]: Size of attempted access (in bytes)."

     --#SUMMARY "An attempt to write to a device on the PM's I2C bus has failed."
     --#ARGUMENTS {}
     --#SEVERITY WARNING
     --#TIMEINDEX 100
     --#STATE OPERATIONAL
::= 8212


hpevtPmI2cReadFailed TRAP-TYPE
     ENTERPRISE hpIpfE0Events
     VARIABLES { hpIpfEvtDetailStr }
     DESCRIPTION
        "An attempt to read from a device on the PM's I2C bus has failed.  This event is only emitted when the PM is reading a BPS's.  

The Data field contains information that can identify the exact device that has failed. Refer to the UGUY ERS for a mapping of I2C device addresses to devices. 
Data Bytes[0-1]: Reserved 
Data Bytes[2-3]: I2C Device Address (to convert to BPS slot number subtract 1 and divide by 2) 
Data Bytes[4-5]: Starting Word Address 
Data Bytes[6-7]: Size of attempted access (in bytes)."

     --#SUMMARY "An attempt to read from a device on the PM's I2C bus has failed."
     --#ARGUMENTS {}
     --#SEVERITY WARNING
     --#TIMEINDEX 100
     --#STATE OPERATIONAL
::= 8214


hpevtCellInfoError TRAP-TYPE
     ENTERPRISE hpIpfE0Events
     VARIABLES { hpIpfEvtDetailStr }
     DESCRIPTION
        "An error was encountered trying to obtain the data required for the cell information structure in ICM.  The data field is an ASCII message that indicates the information that was not found."

     --#SUMMARY "An error was encountered updating the cell info structure in ICM"
     --#ARGUMENTS {}
     --#SEVERITY WARNING
     --#TIMEINDEX 100
     --#STATE OPERATIONAL
::= 8216


hpevtSlaveConsoleSetupError TRAP-TYPE
     ENTERPRISE hpIpfE0Events
     VARIABLES { hpIpfEvtDetailStr }
     DESCRIPTION
        "An error was encountered establishing the slave cells use of the diva console."

     --#SUMMARY "An error was encountered pointing the slave cell consoles to the diva"
     --#ARGUMENTS {}
     --#SEVERITY WARNING
     --#TIMEINDEX 100
     --#STATE OPERATIONAL
::= 8218


hpevtRegistryMoveToCoreCellError TRAP-TYPE
     ENTERPRISE hpIpfE0Events
     VARIABLES { hpIpfEvtDetailStr }
     DESCRIPTION
        "An error was encountered trying to relocate the registry on a slave cell to point to the core cells main memory strucutres."

     --#SUMMARY "An error was encountered trying to relocate a slave cells registry"
     --#ARGUMENTS {}
     --#SEVERITY CRITICAL
     --#TIMEINDEX 100
     --#STATE OPERATIONAL
::= 8219


hpevtProfileGroupCCrcError TRAP-TYPE
     ENTERPRISE hpIpfE0Events
     VARIABLES { hpIpfEvtDetailStr }
     DESCRIPTION
        "The Calculuated CRC for the group C Partition Profile did not match the stored value.  The expected value and the actual value will be emmited in 2 sequential chassis codes."

     --#SUMMARY "Complex Profile Group C CRC didn't match the expected value"
     --#ARGUMENTS {}
     --#SEVERITY CRITICAL
     --#TIMEINDEX 100
     --#STATE OPERATIONAL
::= 8220


hpevtMcCoreCellSelectFail TRAP-TYPE
     ENTERPRISE hpIpfE0Events
     VARIABLES { hpIpfEvtDetailStr }
     DESCRIPTION
        "Not able to find a core cell in the PD during a global MCA error processing."

     --#SUMMARY "Failure to identify a core cell during Global MCA."
     --#ARGUMENTS {}
     --#SEVERITY CRITICAL
     --#TIMEINDEX 100
     --#STATE OPERATIONAL
::= 8238


hpevtFabricAssertFabricUtils TRAP-TYPE
     ENTERPRISE hpIpfE0Events
     VARIABLES { hpIpfEvtDetailStr }
     DESCRIPTION
        "An unexpected error occurred while initializing the fabric.  The firmware is not able to analyze this error.  Clues to the cause of this error may be found in the IPMI forward progress log (FPL) either shortly before or after this log entry occurred.  The FPL is available from the management processor using the 'sl' command.  HP-UX also saves these logs in the /var/stm/logs/os directory, and they can be viewed using the slview utility."

     --#SUMMARY "Unexpected fabric firmware error"
     --#ARGUMENTS {}
     --#SEVERITY WARNING
     --#TIMEINDEX 100
     --#STATE OPERATIONAL
::= 8239


hpevtSalPmiFwError TRAP-TYPE
     ENTERPRISE hpIpfE0Events
     VARIABLES { hpIpfEvtDetailStr }
     DESCRIPTION
        "An internal firmware error was encountered.  This is usually caused by a bad parameter passed to a function, corrupt memory, corrupt malloc tables or something similar.  The data field contains the IP address of the function that encountered the error."

     --#SUMMARY "Internal firmware programming error in the PMI handler."
     --#ARGUMENTS {}
     --#SEVERITY CRITICAL
     --#TIMEINDEX 100
     --#STATE OPERATIONAL
::= 8240


hpevtOlaWrongNumberCells TRAP-TYPE
     ENTERPRISE hpIpfE0Events
     VARIABLES { hpIpfEvtDetailStr }
     DESCRIPTION
        "During the on line addition of a cell the partition adding the cell has determined inconsistent data as to which cell is being added.  The cell addition will be aborted and the partition will resume execution without the new cell."

     --#SUMMARY "During a Cell On Line Add inconsistent number of cells discovered"
     --#ARGUMENTS {}
     --#SEVERITY CRITICAL
     --#TIMEINDEX 100
     --#STATE OPERATIONAL
::= 8243


hpevtFabricXbcRouteSourceCellPortErr TRAP-TYPE
     ENTERPRISE hpIpfE0Events
     VARIABLES { hpIpfEvtDetailStr }
     DESCRIPTION
        "An error occurred while reading the routing from the source cell's port on the source XBC.  Data Field: (source cell << 56 | source XBC << 32)"

     --#SUMMARY "Error reading source cell port on XBC during data traversability test"
     --#ARGUMENTS {}
     --#SEVERITY WARNING
     --#TIMEINDEX 100
     --#STATE OPERATIONAL
::= 8257


hpevtBootMixedCpuCoreFreqInstalled TRAP-TYPE
     ENTERPRISE hpIpfE0Events
     VARIABLES { hpIpfEvtDetailStr }
     DESCRIPTION
        "CPU's of mixed maximum core frequencies are installed"

     --#SUMMARY "CPUs of different maximum core frequencies are installed"
     --#ARGUMENTS {}
     --#SEVERITY WARNING
     --#TIMEINDEX 100
     --#STATE OPERATIONAL
::= 8269


hpevtXinInitIntermittentFailure TRAP-TYPE
     ENTERPRISE hpIpfE0Events
     VARIABLES { hpIpfEvtDetailStr }
     DESCRIPTION
        "The Cell Controller-XBC link initialization is having an intermittent failure.  The data field contains the number of initialization sequences that failed before being successful."

     --#SUMMARY "The RVL CC-Togo link initialization workaround (PS221) failed"
     --#ARGUMENTS {}
     --#SEVERITY CRITICAL
     --#TIMEINDEX 100
     --#STATE OPERATIONAL
::= 8271


hpevtPdhErrClearOlaSteeringBit TRAP-TYPE
     ENTERPRISE hpIpfE0Events
     VARIABLES { hpIpfEvtDetailStr }
     DESCRIPTION
        "PDC failed clearing the OLA steering bit in the PDH FPGA microstatus register.  Data field contains the physical location of the cell with the failure.  This can only happen on an OLA cell and will cause that cell to reset and not to join the existing partition."

     --#SUMMARY "PDC failed clearing the OLA steering bit in the Dillon microstatus reg."
     --#ARGUMENTS {}
     --#SEVERITY WARNING
     --#TIMEINDEX 100
     --#STATE OPERATIONAL
::= 8643


hpevtFabricCc2XbcLinkInitFailed TRAP-TYPE
     ENTERPRISE hpIpfE0Events
     VARIABLES { hpIpfEvtDetailStr }
     DESCRIPTION
        "Fabric Discovery's final attempt to initialize the local cell's CC to Crossbar Chip (XBC) link has failed.  This cell cannot talk to the fabric.  Data: link init state bit read from the CC Link State register"

     --#SUMMARY "Fabric Discovery could not initialize the local cell's XBC link"
     --#ARGUMENTS {}
     --#SEVERITY CRITICAL
     --#TIMEINDEX 100
     --#STATE OPERATIONAL
::= 8648


hpevtFwVirtualMappingError TRAP-TYPE
     ENTERPRISE hpIpfE0Events
     VARIABLES { hpIpfEvtDetailStr }
     DESCRIPTION
        "An internal firmware error was encountered.  This is usually caused by a bad parameter passed to a function, corrupt memory, corrupt malloc tables or something similar.  The data field contains the physical address that failed mapping to a virtual address"

     --#SUMMARY "Internal firmware programming error"
     --#ARGUMENTS {}
     --#SEVERITY CRITICAL
     --#TIMEINDEX 100
     --#STATE OPERATIONAL
::= 8652


hpevtFabricXinInitWriteErr TRAP-TYPE
     ENTERPRISE hpIpfE0Events
     VARIABLES { hpIpfEvtDetailStr }
     DESCRIPTION
        "Failure while writing the XBC CSR containing the link status"

     --#SUMMARY "Error writing the XIN init disable register."
     --#ARGUMENTS {}
     --#SEVERITY CRITICAL
     --#TIMEINDEX 100
     --#STATE OPERATIONAL
::= 8676


hpevtFabricXinInitReadErr TRAP-TYPE
     ENTERPRISE hpIpfE0Events
     VARIABLES { hpIpfEvtDetailStr }
     DESCRIPTION
        "Failure while reading the XBC CSR containing the link status"

     --#SUMMARY "Error reading the XIN init state register."
     --#ARGUMENTS {}
     --#SEVERITY CRITICAL
     --#TIMEINDEX 100
     --#STATE OPERATIONAL
::= 8677


hpevtFabricLinkInitIntermittentFailure TRAP-TYPE
     ENTERPRISE hpIpfE0Events
     VARIABLES { hpIpfEvtDetailStr }
     DESCRIPTION
        "Fabric Discovery's attempt to initialize the local cell's CC to XBC link has failed.  The link initialization sequence has an intermittent problem."

     --#SUMMARY "intermittent failure while retrying the CC to XBC link init"
     --#ARGUMENTS {}
     --#SEVERITY CRITICAL
     --#TIMEINDEX 100
     --#STATE OPERATIONAL
::= 8679


hpevtIodiscPciInitnodeError TRAP-TYPE
     ENTERPRISE hpIpfE0Events
     VARIABLES { hpIpfEvtDetailStr }
     DESCRIPTION
        "An error was encountered while attempting to create and initialize a PCI device node"

     --#SUMMARY "Initialization of a PCI node in the firmware device tree failed"
     --#ARGUMENTS {}
     --#SEVERITY WARNING
     --#TIMEINDEX 100
     --#STATE OPERATIONAL
::= 8690


hpevtIodiscPciBusscanError TRAP-TYPE
     ENTERPRISE hpIpfE0Events
     VARIABLES { hpIpfEvtDetailStr }
     DESCRIPTION
        "An error was encountered while scanning the PCI bus"

     --#SUMMARY "An error was encountered while scanning the PCI bus."
     --#ARGUMENTS {}
     --#SEVERITY CRITICAL
     --#TIMEINDEX 100
     --#STATE OPERATIONAL
::= 8691


hpevtIodiscPciInitbridgeError TRAP-TYPE
     ENTERPRISE hpIpfE0Events
     VARIABLES { hpIpfEvtDetailStr }
     DESCRIPTION
        "An error was encountered while attempting to initialize a P2P bridge"

     --#SUMMARY "An error was encountered initializing the PCI bridge"
     --#ARGUMENTS {}
     --#SEVERITY WARNING
     --#TIMEINDEX 100
     --#STATE OPERATIONAL
::= 8692


hpevtIodiscPciIomapError TRAP-TYPE
     ENTERPRISE hpIpfE0Events
     VARIABLES { hpIpfEvtDetailStr }
     DESCRIPTION
        "Insufficient IO Port space to support the PCI card"

     --#SUMMARY "An error was encountered initializing the PCI IO map."
     --#ARGUMENTS {}
     --#SEVERITY WARNING
     --#TIMEINDEX 100
     --#STATE OPERATIONAL
::= 8693


hpevtIodiscPciMmiomapError TRAP-TYPE
     ENTERPRISE hpIpfE0Events
     VARIABLES { hpIpfEvtDetailStr }
     DESCRIPTION
        "Insufficient MMIO space to support the PCI card requirements"

     --#SUMMARY "An error was encountered creating the PCI MMIO map"
     --#ARGUMENTS {}
     --#SEVERITY WARNING
     --#TIMEINDEX 100
     --#STATE OPERATIONAL
::= 8694


hpevtIodiscSbaInitnodeError TRAP-TYPE
     ENTERPRISE hpIpfE0Events
     VARIABLES { hpIpfEvtDetailStr }
     DESCRIPTION
        "An error was encountered while attempting to initialize the SBA node"

     --#SUMMARY "There was an error initializing the SBA node"
     --#ARGUMENTS {}
     --#SEVERITY CRITICAL
     --#TIMEINDEX 100
     --#STATE OPERATIONAL
::= 8709


hpevtIodiscSbaDiscoverError TRAP-TYPE
     ENTERPRISE hpIpfE0Events
     VARIABLES { hpIpfEvtDetailStr }
     DESCRIPTION
        "An error was encountered while attempting to discover SBA hardware"

     --#SUMMARY "There was an error discovering the SBA"
     --#ARGUMENTS {}
     --#SEVERITY CRITICAL
     --#TIMEINDEX 100
     --#STATE OPERATIONAL
::= 8710


hpevtIodiscSbaResetError TRAP-TYPE
     ENTERPRISE hpIpfE0Events
     VARIABLES { hpIpfEvtDetailStr }
     DESCRIPTION
        "An error was encountered while attempting to reset the SBA"

     --#SUMMARY "An error was encountered while resetting the SBA"
     --#ARGUMENTS {}
     --#SEVERITY CRITICAL
     --#TIMEINDEX 100
     --#STATE OPERATIONAL
::= 8711


hpevtIodiscIolinkError TRAP-TYPE
     ENTERPRISE hpIpfE0Events
     VARIABLES { hpIpfEvtDetailStr }
     DESCRIPTION
        "An error was detected in the link berween the CC and the I/O controller."

     --#SUMMARY "There was an error initializing the IO link"
     --#ARGUMENTS {}
     --#SEVERITY WARNING
     --#TIMEINDEX 100
     --#STATE OPERATIONAL
::= 8712


hpevtIodiscCableError TRAP-TYPE
     ENTERPRISE hpIpfE0Events
     VARIABLES { hpIpfEvtDetailStr }
     DESCRIPTION
        "An SBA cable error has been detected"

     --#SUMMARY "There is a problem initializing the REO cable"
     --#ARGUMENTS {}
     --#SEVERITY WARNING
     --#TIMEINDEX 100
     --#STATE OPERATIONAL
::= 8713


hpevtIodiscIoChassisPower TRAP-TYPE
     ENTERPRISE hpIpfE0Events
     VARIABLES { hpIpfEvtDetailStr }
     DESCRIPTION
        "Identified the cell number that is connected to the chassis."

     --#SUMMARY "The IO chassis discovered was powered off"
     --#ARGUMENTS {}
     --#SEVERITY CRITICAL
     --#TIMEINDEX 100
     --#STATE OPERATIONAL
::= 8714


hpevtIodiscLbaInitnodeError TRAP-TYPE
     ENTERPRISE hpIpfE0Events
     VARIABLES { hpIpfEvtDetailStr }
     DESCRIPTION
        "An error occurred while attempting to create or initialize an LBA node"

     --#SUMMARY "There was an error initializing the LBA"
     --#ARGUMENTS {}
     --#SEVERITY WARNING
     --#TIMEINDEX 100
     --#STATE OPERATIONAL
::= 8715


hpevtIodiscLbaWidthError TRAP-TYPE
     ENTERPRISE hpIpfE0Events
     VARIABLES { hpIpfEvtDetailStr }
     DESCRIPTION
        "An error was encountered while attempting to configure LBA rope bundling width"

     --#SUMMARY "There was an error querying the LBA width"
     --#ARGUMENTS {}
     --#SEVERITY CRITICAL
     --#TIMEINDEX 100
     --#STATE OPERATIONAL
::= 8716


hpevtIodiscLbaPhaseError TRAP-TYPE
     ENTERPRISE hpIpfE0Events
     VARIABLES { hpIpfEvtDetailStr }
     DESCRIPTION
        "error code"

     --#SUMMARY "There was an error with the LBA phase"
     --#ARGUMENTS {}
     --#SEVERITY WARNING
     --#TIMEINDEX 100
     --#STATE OPERATIONAL
::= 8717


hpevtIodiscLbaClearError TRAP-TYPE
     ENTERPRISE hpIpfE0Events
     VARIABLES { hpIpfEvtDetailStr }
     DESCRIPTION
        "An error occurred while attempting to clear an LBA error log register"

     --#SUMMARY "There was an error clearing the LBA"
     --#ARGUMENTS {}
     --#SEVERITY WARNING
     --#TIMEINDEX 100
     --#STATE OPERATIONAL
::= 8718


hpevtIodiscLbaLogError TRAP-TYPE
     ENTERPRISE hpIpfE0Events
     VARIABLES { hpIpfEvtDetailStr }
     DESCRIPTION
        "An error was encountered while attempting to generate LBA error logs"

     --#SUMMARY "There was an error with the LBA log"
     --#ARGUMENTS {}
     --#SEVERITY CRITICAL
     --#TIMEINDEX 100
     --#STATE OPERATIONAL
::= 8719


hpevtIodiscLbaDiscoverError TRAP-TYPE
     ENTERPRISE hpIpfE0Events
     VARIABLES { hpIpfEvtDetailStr }
     DESCRIPTION
        "An error was encountered while attempting to discover LBA hardware"

     --#SUMMARY "There was an error discovering the LBA"
     --#ARGUMENTS {}
     --#SEVERITY CRITICAL
     --#TIMEINDEX 100
     --#STATE OPERATIONAL
::= 8720


hpevtIodiscLbaConfigError TRAP-TYPE
     ENTERPRISE hpIpfE0Events
     VARIABLES { hpIpfEvtDetailStr }
     DESCRIPTION
        "An error occurred while attempting to configure the LBA hardware"

     --#SUMMARY "There was an error configuring the LBA"
     --#ARGUMENTS {}
     --#SEVERITY WARNING
     --#TIMEINDEX 100
     --#STATE OPERATIONAL
::= 8721


hpevtIodiscLbaPciscanError TRAP-TYPE
     ENTERPRISE hpIpfE0Events
     VARIABLES { hpIpfEvtDetailStr }
     DESCRIPTION
        "An error was encountered while attempting to scan the PCI bus"

     --#SUMMARY "There was an error scanning the PCI bus"
     --#ARGUMENTS {}
     --#SEVERITY CRITICAL
     --#TIMEINDEX 100
     --#STATE OPERATIONAL
::= 8722


hpevtIodiscLbaPciconfigError TRAP-TYPE
     ENTERPRISE hpIpfE0Events
     VARIABLES { hpIpfEvtDetailStr }
     DESCRIPTION
        "An error was encountered while attempting to configure PCI config space"

     --#SUMMARY "There was an error configuring PCI space through the LBA"
     --#ARGUMENTS {}
     --#SEVERITY CRITICAL
     --#TIMEINDEX 100
     --#STATE OPERATIONAL
::= 8723


hpevtBootFwRelocMemErr TRAP-TYPE
     ENTERPRISE hpIpfE0Events
     VARIABLES { hpIpfEvtDetailStr }
     DESCRIPTION
        "A Firmware tries to find a main memory block large enough meeting alignment requirements."

     --#SUMMARY "Firmware was unable to find a suitable block of main memory to relocate ROM"
     --#ARGUMENTS {}
     --#SEVERITY CRITICAL
     --#TIMEINDEX 100
     --#STATE OPERATIONAL
::= 8747


hpevtOptsNvmAllocError TRAP-TYPE
     ENTERPRISE hpIpfE0Events
     VARIABLES { hpIpfEvtDetailStr }
     DESCRIPTION
        "The Options service received an error when attempting to allocate an NVRAM storage block. Either an error was returned from the call, or the call returned successfully yet an invalid address was returned."

     --#SUMMARY "The Options service received an NVRAM allocation error."
     --#ARGUMENTS {}
     --#SEVERITY CRITICAL
     --#TIMEINDEX 100
     --#STATE OPERATIONAL
::= 8756


hpevtSalInfoTimeout TRAP-TYPE
     ENTERPRISE hpIpfE0Events
     VARIABLES { hpIpfEvtDetailStr }
     DESCRIPTION
        "Access to SAL error log procedure timed out because the log facility was busy processing a request from another CPU.  Data field indicates the SAL procedure ID."

     --#SUMMARY "SAL errlog access timeout"
     --#ARGUMENTS {}
     --#SEVERITY WARNING
     --#TIMEINDEX 100
     --#STATE OPERATIONAL
::= 8758


hpevtPdhIprNotClearedOnCell TRAP-TYPE
     ENTERPRISE hpIpfE0Events
     VARIABLES { hpIpfEvtDetailStr }
     DESCRIPTION
        "The PDH FPGA IPR is not cleared after a MAX_RD_CLR_IPR_TRIES on a cell.  The Data Filed in the Cell number. 
See the next Chassis Code to see the MAX_RD_CLR_IPR_TRIES"

     --#SUMMARY "The Dillon IPR is not cleared after a MAX_RD_CLR_IPR_TRIES on a cell."
     --#ARGUMENTS {}
     --#SEVERITY WARNING
     --#TIMEINDEX 100
     --#STATE OPERATIONAL
::= 8761


hpevtPdhIprClearAttempts TRAP-TYPE
     ENTERPRISE hpIpfE0Events
     VARIABLES { hpIpfEvtDetailStr }
     DESCRIPTION
        "Indicated the PDH FPGA IPR is not cleared after a number of PDC attemps.  The Data Field contens the MAX_RD_CLR_IPR_TRIES.  Please look at the previous Chassis Code to see the Cell number."

     --#SUMMARY "Indicated the Dillon IPR is not cleared after a number of PDC attemps."
     --#ARGUMENTS {}
     --#SEVERITY WARNING
     --#TIMEINDEX 100
     --#STATE OPERATIONAL
::= 8762


hpevtMemIncompleteEchelon TRAP-TYPE
     ENTERPRISE hpIpfE0Events
     VARIABLES { hpIpfEvtDetailStr }
     DESCRIPTION
        "One or more dimms are missing from the echelon given in the data field.  The dimms may not be installed or firmware was not able to detect the dimms."

     --#SUMMARY "The echelon given in the data field is not fully populated."
     --#ARGUMENTS {}
     --#SEVERITY WARNING
     --#TIMEINDEX 100
     --#STATE OPERATIONAL
::= 8768


hpevtFabricRdPortStatePortInvalid TRAP-TYPE
     ENTERPRISE hpIpfE0Events
     VARIABLES { hpIpfEvtDetailStr }
     DESCRIPTION
        "The code that reads the port state (landmine vs. healthy) expects a XBC internal port number, it received bogus data.  The port state cannot be read.  Data Field: (port << 44) | (xbc num << 32)"

     --#SUMMARY "Attempted to read the port state from an illegal port number"
     --#ARGUMENTS {}
     --#SEVERITY WARNING
     --#TIMEINDEX 100
     --#STATE OPERATIONAL
::= 8771


hpevtFabricWrPortStatePortInvalid TRAP-TYPE
     ENTERPRISE hpIpfE0Events
     VARIABLES { hpIpfEvtDetailStr }
     DESCRIPTION
        "The code that writes the port state (landmine vs. healthy) expects a XBC internal port number, it received bogus data.  The port state cannot be read.  Data Field: (port << 44) | (xbc num << 32)"

     --#SUMMARY "Attempted to write the port state for an illegal port"
     --#ARGUMENTS {}
     --#SEVERITY WARNING
     --#TIMEINDEX 100
     --#STATE OPERATIONAL
::= 8772


hpevtMainBpLpmFlt TRAP-TYPE
     ENTERPRISE hpIpfE0Events
     VARIABLES { hpIpfEvtDetailStr }
     DESCRIPTION
        "The main backplane is reporting the LPM status as fault."

     --#SUMMARY "The main backplane is reporting the LPM status as fault."
     --#ARGUMENTS {}
     --#SEVERITY WARNING
     --#TIMEINDEX 100
     --#STATE OPERATIONAL
::= 8784


hpevtIoBpLpmFlt TRAP-TYPE
     ENTERPRISE hpIpfE0Events
     VARIABLES { hpIpfEvtDetailStr }
     DESCRIPTION
        "The IO backplane has reported a local power monitor fault."

     --#SUMMARY "The IO backplane is reporting a LPM status as fault."
     --#ARGUMENTS {}
     --#SEVERITY WARNING
     --#TIMEINDEX 100
     --#STATE OPERATIONAL
::= 8787


hpevtCmplxProfileInitFailed TRAP-TYPE
     ENTERPRISE hpIpfE0Events
     VARIABLES { hpIpfEvtDetailStr }
     DESCRIPTION
        "System firmware was unable to default the complex profile"

     --#SUMMARY "System firmware was unable to default the complex profile"
     --#ARGUMENTS {}
     --#SEVERITY CRITICAL
     --#TIMEINDEX 100
     --#STATE OPERATIONAL
::= 8797


hpevtPalSetProcFeaturesFailed TRAP-TYPE
     ENTERPRISE hpIpfE0Events
     VARIABLES { hpIpfEvtDetailStr }
     DESCRIPTION
        "Firmware call to set processor feature resulted in an error."

     --#SUMMARY "Firmware could not set Pal Proc features"
     --#ARGUMENTS {}
     --#SEVERITY WARNING
     --#TIMEINDEX 100
     --#STATE OPERATIONAL
::= 8798


hpevtActiveLogNotFound TRAP-TYPE
     ENTERPRISE hpIpfE0Events
     VARIABLES { hpIpfEvtDetailStr }
     DESCRIPTION
        "This chassis code shows that the error log space in the NVRAM has not been allocated for the current error event. This will be emitted out whenever a error section is attempted to be logged without allocation of log space in NVRAM"

     --#SUMMARY "Means that the error log space in the Nvram has not been allocated."
     --#ARGUMENTS {}
     --#SEVERITY WARNING
     --#TIMEINDEX 100
     --#STATE OPERATIONAL
::= 8806


hpevtReachedMaxErrorLogs TRAP-TYPE
     ENTERPRISE hpIpfE0Events
     VARIABLES { hpIpfEvtDetailStr }
     DESCRIPTION
        "This indicates that the error logs for a particular event type have reached the maximum allowed to be stored in the NVRAM. The event type is indicated in the data field."

     --#SUMMARY "This indicates the maximum number of logs for the event."
     --#ARGUMENTS {}
     --#SEVERITY WARNING
     --#TIMEINDEX 100
     --#STATE OPERATIONAL
::= 8807


hpevtOldNoCellToDelete TRAP-TYPE
     ENTERPRISE hpIpfE0Events
     VARIABLES { hpIpfEvtDetailStr }
     DESCRIPTION
        "System firmware has been invoked to perform a cell delete operation but no cell in the system appears to be ready for deletion."

     --#SUMMARY "On Line Delete operation was begun but firmware couldn't find a deletable cell"
     --#ARGUMENTS {}
     --#SEVERITY WARNING
     --#TIMEINDEX 100
     --#STATE OPERATIONAL
::= 8814


hpevtBpsOvercurrent TRAP-TYPE
     ENTERPRISE hpIpfE0Events
     VARIABLES { hpIpfEvtDetailStr }
     DESCRIPTION
        "The bulk power supply is overcurrent"

     --#SUMMARY "The bulk power system is above its current capacity."
     --#ARGUMENTS {}
     --#SEVERITY CRITICAL
     --#TIMEINDEX 100
     --#STATE OPERATIONAL
::= 8817


hpevtBpsWarnOt TRAP-TYPE
     ENTERPRISE hpIpfE0Events
     VARIABLES { hpIpfEvtDetailStr }
     DESCRIPTION
        "Data: Bulk location."

     --#SUMMARY "The bulk specified is warning of a potential thermal problem."
     --#ARGUMENTS {}
     --#SEVERITY WARNING
     --#TIMEINDEX 100
     --#STATE OPERATIONAL
::= 8818


hpevtErmOutOfHeap TRAP-TYPE
     ENTERPRISE hpIpfE0Events
     VARIABLES { hpIpfEvtDetailStr }
     DESCRIPTION
        "Error Response Mode code attempted a malloc of heap space that failed."

     --#SUMMARY "Malloc failed while trying to process and ERM"
     --#ARGUMENTS {}
     --#SEVERITY CRITICAL
     --#TIMEINDEX 100
     --#STATE OPERATIONAL
::= 8819


hpevtMemDimmUnsupported TRAP-TYPE
     ENTERPRISE hpIpfE0Events
     VARIABLES { hpIpfEvtDetailStr }
     DESCRIPTION
        "The dimm in the physical location given by the data field is not supported on this platform.  The dimm may not be supported by the hardware, or the dimm may not have been properly qualified for this platform."

     --#SUMMARY "Dimm at physical location in data field is not supported on this platform."
     --#ARGUMENTS {}
     --#SEVERITY WARNING
     --#TIMEINDEX 100
     --#STATE OPERATIONAL
::= 8821


hpevtOptsMallocError TRAP-TYPE
     ENTERPRISE hpIpfE0Events
     VARIABLES { hpIpfEvtDetailStr }
     DESCRIPTION
        "The OPTIONS component was unable to allocate NVRAM memory in order to store a non-volatile variable. The storage area for NVRAM options may be full, or there may be undetected corruption."

     --#SUMMARY "The OPTIONS component received a memory allocation error."
     --#ARGUMENTS {}
     --#SEVERITY CRITICAL
     --#TIMEINDEX 100
     --#STATE OPERATIONAL
::= 8828


hpevtCellHwDegraded TRAP-TYPE
     ENTERPRISE hpIpfE0Events
     VARIABLES { hpIpfEvtDetailStr }
     DESCRIPTION
        "A dimm or CPU has failed and is not operational for the system.  This event is emmitted prior to determining if the cell should be integrated into the Partition."

     --#SUMMARY "A dimm or CPU has been deconfigured or failed testing"
     --#ARGUMENTS {}
     --#SEVERITY WARNING
     --#TIMEINDEX 100
     --#STATE OPERATIONAL
::= 8837


hpevtNotIntegratingCell TRAP-TYPE
     ENTERPRISE hpIpfE0Events
     VARIABLES { hpIpfEvtDetailStr }
     DESCRIPTION
        "A cpu or dimm error has been detected, and the Complex Profile, Cell Integration Table, Cell integration policy says to not integrate the cell into the PD.  The data field is unused, but the cell that emitted this event is the one that did not get integrated."

     --#SUMMARY "The cell will not join the PD"
     --#ARGUMENTS {}
     --#SEVERITY CRITICAL
     --#TIMEINDEX 100
     --#STATE OPERATIONAL
::= 8839


hpevtIoContextCorruptErr TRAP-TYPE
     ENTERPRISE hpIpfE0Events
     VARIABLES { hpIpfEvtDetailStr }
     DESCRIPTION
        "The IO error context is corrupt.  This will impair IO error reporting."

     --#SUMMARY "The error context in NVM was corrupt"
     --#ARGUMENTS {}
     --#SEVERITY WARNING
     --#TIMEINDEX 100
     --#STATE OPERATIONAL
::= 8842


hpevtIoRopeFatal TRAP-TYPE
     ENTERPRISE hpIpfE0Events
     VARIABLES { hpIpfEvtDetailStr }
     DESCRIPTION
        "A rope went fatal from the SBA to the LBA.  If all the ropes go fatal the IO subsystem is dead.  Any I/O below the rope will not be accessible.  The data field gives the physical location of the rope that went fatal.  Some ROPE_FATAL conditions will not cause the system to go down.  For Example, a rope that has gone fatal during an OLAR operation will only cause warnings to the user, not bring the partition down."

     --#SUMMARY "A rope went fatal from the SBA"
     --#ARGUMENTS {}
     --#SEVERITY WARNING
     --#TIMEINDEX 100
     --#STATE OPERATIONAL
::= 8843


hpevtIoBusFatal TRAP-TYPE
     ENTERPRISE hpIpfE0Events
     VARIABLES { hpIpfEvtDetailStr }
     DESCRIPTION
        "A PCI bus on the system is fatal.  Any device on this bus is unavailable.  Firmware was unable to complete card initialization due to an error.  Data field contains physical location of failed bus."

     --#SUMMARY "A PCI bus on the system went fatal."
     --#ARGUMENTS {}
     --#SEVERITY WARNING
     --#TIMEINDEX 100
     --#STATE OPERATIONAL
::= 8844


hpevtIoRopeUnitFatal TRAP-TYPE
     ENTERPRISE hpIpfE0Events
     VARIABLES { hpIpfEvtDetailStr }
     DESCRIPTION
        "One of the rope units in the SBA failed.  If all of the rope units fail, then IO will not be available on this cell."

     --#SUMMARY "One of the rope units in the SBA is dead."
     --#ARGUMENTS {}
     --#SEVERITY WARNING
     --#TIMEINDEX 100
     --#STATE OPERATIONAL
::= 8845


hpevtPdhFlashWriteEnableBitSetNowCleared TRAP-TYPE
     ENTERPRISE hpIpfE0Events
     VARIABLES { hpIpfEvtDetailStr }
     DESCRIPTION
        "The System Flash Write Enable bit is incorrectly set and now clearing by PDC.  The Data fileld contains the value of  PDH Miscellaneous Signal Register read before System Flash bit is cleared."

     --#SUMMARY "The System Flash Write Enable bit is incorrectly set and now clearing by PDC"
     --#ARGUMENTS {}
     --#SEVERITY WARNING
     --#TIMEINDEX 100
     --#STATE OPERATIONAL
::= 8851


hpevtFirmwareInitError TRAP-TYPE
     ENTERPRISE hpIpfE0Events
     VARIABLES { hpIpfEvtDetailStr }
     DESCRIPTION
        "System firmware encountered an error while trying to perform an operation during system initialization.  This event ID will always be emmitted before an event ID that describes the status of the operation that failed."

     --#SUMMARY "Firmware encountered a problem trying to initialize"
     --#ARGUMENTS {}
     --#SEVERITY CRITICAL
     --#TIMEINDEX 100
     --#STATE OPERATIONAL
::= 8855


hpevtMcIncompleteCpuSet TRAP-TYPE
     ENTERPRISE hpIpfE0Events
     VARIABLES { hpIpfEvtDetailStr }
     DESCRIPTION
        "This means that all the cpus in the cell did not show up."

     --#SUMMARY "This means that all the cpus in the cell did not show up."
     --#ARGUMENTS {}
     --#SEVERITY WARNING
     --#TIMEINDEX 100
     --#STATE OPERATIONAL
::= 8857


hpevtMcIncompleteCellSet TRAP-TYPE
     ENTERPRISE hpIpfE0Events
     VARIABLES { hpIpfEvtDetailStr }
     DESCRIPTION
        "This means that all the cells did not rendezvous during the PD rendezvous. The data part will contain the Expected data and the actual mask of the cells that rendezvoused."

     --#SUMMARY "This means that all the cells did not rendezvous during the PD rendezvous."
     --#ARGUMENTS {}
     --#SEVERITY WARNING
     --#TIMEINDEX 100
     --#STATE OPERATIONAL
::= 8858


hpevtMcTreeCheckFailed TRAP-TYPE
     ENTERPRISE hpIpfE0Events
     VARIABLES { hpIpfEvtDetailStr }
     DESCRIPTION
        "The FW tree sanity check failed during the MCA error processing."

     --#SUMMARY "The FW tree sanity check failed during the MCA error processing."
     --#ARGUMENTS {}
     --#SEVERITY WARNING
     --#TIMEINDEX 100
     --#STATE OPERATIONAL
::= 8859


hpevtMcRegistryCheckFailed TRAP-TYPE
     ENTERPRISE hpIpfE0Events
     VARIABLES { hpIpfEvtDetailStr }
     DESCRIPTION
        "This means that the registry sanity check failed during MCA error handling."

     --#SUMMARY "This means that the registry sanity check failed during MCA error handling."
     --#ARGUMENTS {}
     --#SEVERITY WARNING
     --#TIMEINDEX 100
     --#STATE OPERATIONAL
::= 8860


hpevtMcDuringOsMca TRAP-TYPE
     ENTERPRISE hpIpfE0Events
     VARIABLES { hpIpfEvtDetailStr }
     DESCRIPTION
        "This means that MCA occurred while OS_MCA was performing error recovery."

     --#SUMMARY "This means that MCA occurred while OS_MCA was parforming error recovery."
     --#ARGUMENTS {}
     --#SEVERITY WARNING
     --#TIMEINDEX 100
     --#STATE OPERATIONAL
::= 8861


hpevtMcMemDumpAbandon TRAP-TYPE
     ENTERPRISE hpIpfE0Events
     VARIABLES { hpIpfEvtDetailStr }
     DESCRIPTION
        "This means that memory dump will be abandoned due to work-around for CN2272. This happens when one of the Blocking timout in the Processor input block of the Cell Controller occurs."

     --#SUMMARY "One of the BT errors occurred that results in abandoning memory dump."
     --#ARGUMENTS {}
     --#SEVERITY WARNING
     --#TIMEINDEX 100
     --#STATE OPERATIONAL
::= 8864


hpevtMcFwTreeNotComplete TRAP-TYPE
     ENTERPRISE hpIpfE0Events
     VARIABLES { hpIpfEvtDetailStr }
     DESCRIPTION
        "The firmware tree is not complete and hence there will be no PD rendezvous."

     --#SUMMARY "The firmware tree is not complete and hence there will be no PD rendezvous."
     --#ARGUMENTS {}
     --#SEVERITY WARNING
     --#TIMEINDEX 100
     --#STATE OPERATIONAL
::= 8865


hpevtAcpiConfigMismatch TRAP-TYPE
     ENTERPRISE hpIpfE0Events
     VARIABLES { hpIpfEvtDetailStr }
     DESCRIPTION
        "The firmware parameter that defines the ACPI configuration is inconsistent in at least one of the cells in the partition."

     --#SUMMARY "ACPI configuration mismatch across cells in the partition"
     --#ARGUMENTS {}
     --#SEVERITY CRITICAL
     --#TIMEINDEX 100
     --#STATE OPERATIONAL
::= 8872


hpevtFabricXinErrOrderStatusClrFailed TRAP-TYPE
     ENTERPRISE hpIpfE0Events
     VARIABLES { hpIpfEvtDetailStr }
     DESCRIPTION
        "Writing the XIN_ERR_ORDER_STATUS register of the CC failed.  This is some sort of a hardware failure.  Data Field: return status"

     --#SUMMARY "Failed clearing of the XIN_ERR_ORDER_STATUS CSR"
     --#ARGUMENTS {}
     --#SEVERITY CRITICAL
     --#TIMEINDEX 100
     --#STATE OPERATIONAL
::= 8873


hpevtFabricAssertFabricInit TRAP-TYPE
     ENTERPRISE hpIpfE0Events
     VARIABLES { hpIpfEvtDetailStr }
     DESCRIPTION
        "An unexpected error occurred while initializing the fabric.  The firmware is not able to analyze this error.  Clues to the cause of this error may be found in the IPMI forward progress log (FPL) either shortly before or after this log entry occurred.  The FPL is available from the management processor using the 'sl' command.  HP-UX also saves these logs in the /var/stm/logs/os directory, and they can be viewed using the slview utility."

     --#SUMMARY "Unexpected fabric firmware error"
     --#ARGUMENTS {}
     --#SEVERITY WARNING
     --#TIMEINDEX 100
     --#STATE OPERATIONAL
::= 8876


hpevtInvalidPiromData TRAP-TYPE
     ENTERPRISE hpIpfE0Events
     VARIABLES { hpIpfEvtDetailStr }
     DESCRIPTION
        "A value read by the PDHC from a CPU module's Processor Information ROM was not within acceptable limits."

     --#SUMMARY "Invalid data read from a CPU module's Processor Information ROM."
     --#ARGUMENTS {}
     --#SEVERITY WARNING
     --#TIMEINDEX 100
     --#STATE OPERATIONAL
::= 8877


hpevtSettingFreqRatiosError TRAP-TYPE
     ENTERPRISE hpIpfE0Events
     VARIABLES { hpIpfEvtDetailStr }
     DESCRIPTION
        "An invalid parameter was specified when trying to set the cpu bus config register, cpu frequencies ratio field.  Valid range is 0xe - 0x17"

     --#SUMMARY "Invalid paramater when setting cpu frequency ratios"
     --#ARGUMENTS {}
     --#SEVERITY WARNING
     --#TIMEINDEX 100
     --#STATE OPERATIONAL
::= 8882


hpevtOptsBlockCksumError TRAP-TYPE
     ENTERPRISE hpIpfE0Events
     VARIABLES { hpIpfEvtDetailStr }
     DESCRIPTION
        "The overhead structure of the OPTIONS block in NVRAM has a checksum error."

     --#SUMMARY "Option block in nvram has a checksum error"
     --#ARGUMENTS {}
     --#SEVERITY WARNING
     --#TIMEINDEX 100
     --#STATE OPERATIONAL
::= 8883


hpevtFabricColaLocalCcLinkNotInit TRAP-TYPE
     ENTERPRISE hpIpfE0Events
     VARIABLES { hpIpfEvtDetailStr }
     DESCRIPTION
        "During a cell OLA, the link on the local cell failed to initialize.  Data Field: (my cell << 32) | XIN Link State"

     --#SUMMARY "CC to CC link did not initialize on the local cell"
     --#ARGUMENTS {}
     --#SEVERITY WARNING
     --#TIMEINDEX 100
     --#STATE OPERATIONAL
::= 8894


hpevtFabricXinInitDisableWrError TRAP-TYPE
     ENTERPRISE hpIpfE0Events
     VARIABLES { hpIpfEvtDetailStr }
     DESCRIPTION
        "An attempt to disable the fabric link failed because writing the CC CSR failed.    Data Field: (cell << 56) | return status"

     --#SUMMARY "Failed to write the CC link disable register"
     --#ARGUMENTS {}
     --#SEVERITY WARNING
     --#TIMEINDEX 100
     --#STATE OPERATIONAL
::= 8895


hpevtFabricXinErrMaskUnknownBkp TRAP-TYPE
     ENTERPRISE hpIpfE0Events
     VARIABLES { hpIpfEvtDetailStr }
     DESCRIPTION
        "Could not determine the system type in order to write the appropriate error mask for the fabric link.  Data Field: system type"

     --#SUMMARY "An unknown backplane type was found"
     --#ARGUMENTS {}
     --#SEVERITY WARNING
     --#TIMEINDEX 100
     --#STATE OPERATIONAL
::= 8896


hpevtFabricXinWrErrMaskError TRAP-TYPE
     ENTERPRISE hpIpfE0Events
     VARIABLES { hpIpfEvtDetailStr }
     DESCRIPTION
        "Failed writing the XIN error mask for CC's fabric link.   Data Field: (cell << 56) | return status"

     --#SUMMARY "Error writing the CC link error mask"
     --#ARGUMENTS {}
     --#SEVERITY WARNING
     --#TIMEINDEX 100
     --#STATE OPERATIONAL
::= 8897


hpevtFabricXinRdErrMaskError TRAP-TYPE
     ENTERPRISE hpIpfE0Events
     VARIABLES { hpIpfEvtDetailStr }
     DESCRIPTION
        "Could not read the XIN Link error mask register.  Data Field: (cell << 56) | return status"

     --#SUMMARY "Failed to read the CC's fabric link error mask"
     --#ARGUMENTS {}
     --#SEVERITY WARNING
     --#TIMEINDEX 100
     --#STATE OPERATIONAL
::= 8898


hpevtFabricInitCcLinkFailure TRAP-TYPE
     ENTERPRISE hpIpfE0Events
     VARIABLES { hpIpfEvtDetailStr }
     DESCRIPTION
        "The CC to CC link initialization sequence has failed.  Data Field: link init status"

     --#SUMMARY "Could not initialize the CC to CC link upon boot."
     --#ARGUMENTS {}
     --#SEVERITY CRITICAL
     --#TIMEINDEX 100
     --#STATE OPERATIONAL
::= 8900


hpevtResetCommandError TRAP-TYPE
     ENTERPRISE hpIpfE0Events
     VARIABLES { hpIpfEvtDetailStr }
     DESCRIPTION
        "An error occurred while trying to notify the MP that a reset is about to occure (QPartitionReleaseBIB command).  The status is in the data field."

     --#SUMMARY "An Error occurred trying to notify the MP of the attempted reset."
     --#ARGUMENTS {}
     --#SEVERITY WARNING
     --#TIMEINDEX 100
     --#STATE OPERATIONAL
::= 8906


hpevtErrAssertData TRAP-TYPE
     ENTERPRISE hpIpfE0Events
     VARIABLES { hpIpfEvtDetailStr }
     DESCRIPTION
        "A software error has occurred.  
 
Data field consists of data pertinent to the error. Lab involvement is indicated."

     --#SUMMARY "Error Data tied to a previous Error Assert event"
     --#ARGUMENTS {}
     --#SEVERITY WARNING
     --#TIMEINDEX 100
     --#STATE OPERATIONAL
::= 8924


hpevtFabricInitCcLinkDisableErr TRAP-TYPE
     ENTERPRISE hpIpfE0Events
     VARIABLES { hpIpfEvtDetailStr }
     DESCRIPTION
        "A fabric access error occurred while trying to disable the CC to CC link on a single cell Medel system.  This cell will halt.  Data field: error status"

     --#SUMMARY "Failed disabling the XIN link for a single cell model"
     --#ARGUMENTS {}
     --#SEVERITY WARNING
     --#TIMEINDEX 100
     --#STATE OPERATIONAL
::= 8926


hpevtFabricSetPortStateGetSm4Err TRAP-TYPE
     ENTERPRISE hpIpfE0Events
     VARIABLES { hpIpfEvtDetailStr }
     DESCRIPTION
        "While updating the Port State register, the cell could not get the XBC semaphore.  Data field is: (Port Num << 44 | XBC num << 32 | return status).  Where return status is: (0 Success; -1 Access Failure; -2 Semaphore Owned By Another, -3 Semaphore Already Owned; -4 XBC Key Contention)"

     --#SUMMARY "Error while getting the XBC Semaphore"
     --#ARGUMENTS {}
     --#SEVERITY CRITICAL
     --#TIMEINDEX 100
     --#STATE OPERATIONAL
::= 8930


hpevtFabricSetPortStateRlsSm4Err TRAP-TYPE
     ENTERPRISE hpIpfE0Events
     VARIABLES { hpIpfEvtDetailStr }
     DESCRIPTION
        "While updating the Port State register, the cell could not get the XBC semaphore.  Data field is: (Port Num << 44 | XBC num << 32 | return status).  Where return status is: (0 Success; -1 Generic Failure)"

     --#SUMMARY "Error releasing the XBC Semaphore"
     --#ARGUMENTS {}
     --#SEVERITY WARNING
     --#TIMEINDEX 100
     --#STATE OPERATIONAL
::= 8931


hpevtFabricAssertFabricErr TRAP-TYPE
     ENTERPRISE hpIpfE0Events
     VARIABLES { hpIpfEvtDetailStr }
     DESCRIPTION
        "An unexpected error occurred while initializing the fabric.  The firmware is not able to analyze this error.  Clues to the cause of this error may be found in the IPMI forward progress log (FPL) either shortly before or after this log entry occurred.  The FPL is available from the management processor using the 'sl' command.  HP-UX also saves these logs in the /var/stm/logs/os directory, and they can be viewed using the slview utility."

     --#SUMMARY "Unexpected fabric firmware error"
     --#ARGUMENTS {}
     --#SEVERITY WARNING
     --#TIMEINDEX 100
     --#STATE OPERATIONAL
::= 8936


hpevtFabricXinLinkAlreadyInit TRAP-TYPE
     ENTERPRISE hpIpfE0Events
     VARIABLES { hpIpfEvtDetailStr }
     DESCRIPTION
        "While attempting to initialize the XIN link, it was found to already be initialized.  A firmware assertion has failed.  The link will not be re-initialized and processing should continue as normal.  However, the system could be confused at this point."

     --#SUMMARY "The CC's XIN link was found to be already initialized"
     --#ARGUMENTS {}
     --#SEVERITY WARNING
     --#TIMEINDEX 100
     --#STATE OPERATIONAL
::= 8939


hpevtNoCpuModulesFoundByPdhc TRAP-TYPE
     ENTERPRISE hpIpfE0Events
     VARIABLES { hpIpfEvtDetailStr }
     DESCRIPTION
        "The PDHC FW could not detect any CPU modules on its Cell board, so it is holding the Cell in reset."

     --#SUMMARY "Cell has been disabled by the PDHC because no CPU modules were found."
     --#ARGUMENTS {}
     --#SEVERITY CRITICAL
     --#TIMEINDEX 100
     --#STATE OPERATIONAL
::= 8940


hpevtCpuModCompatMismatch TRAP-TYPE
     ENTERPRISE hpIpfE0Events
     VARIABLES { hpIpfEvtDetailStr }
     DESCRIPTION
        "The Cell has been disabled by PDHC FW because the CPU modules are not compatible. Compatibility is determined based on data stored in the Scratch/FRUID EEPROM on each CPU module. The CPU module partition compatibility byte for each CPU module must be identical."

     --#SUMMARY "Cell has been disabled by PDHC FW because the CPU modules are not compatible."
     --#ARGUMENTS {}
     --#SEVERITY CRITICAL
     --#TIMEINDEX 100
     --#STATE OPERATIONAL
::= 8941


hpevtBadCpuModScratchCksum TRAP-TYPE
     ENTERPRISE hpIpfE0Events
     VARIABLES { hpIpfEvtDetailStr }
     DESCRIPTION
        "The Cell has been disabled because of invalid data in a CPU module Scratch EEPROM. PDHC FW checksums the FRUID data stored in each CPU module's Scratch EEPROM. If a checksum fails, the Cell is held in reset and will not boot. 
The data field identifies the CPU module that failed."

     --#SUMMARY "Cell has been disabled because of invalid data in a CPU module Scratch EEPROM."
     --#ARGUMENTS {}
     --#SEVERITY CRITICAL
     --#TIMEINDEX 100
     --#STATE OPERATIONAL
::= 8942


hpevtPdhBatteryLowWarning TRAP-TYPE
     ENTERPRISE hpIpfE0Events
     VARIABLES { hpIpfEvtDetailStr }
     DESCRIPTION
        "The battery voltage level is low for the cell.  This indicates that the NVRAM will not be saved if the power is removed."

     --#SUMMARY "The Cell Battery voltage level low warning"
     --#ARGUMENTS {}
     --#SEVERITY WARNING
     --#TIMEINDEX 100
     --#STATE OPERATIONAL
::= 8954


hpevtFabricRouteXbcCopyRoutingErr TRAP-TYPE
     ENTERPRISE hpIpfE0Events
     VARIABLES { hpIpfEvtDetailStr }
     DESCRIPTION
        "There was an error while copying the routing for the XBC to the local XBC port.  The cell will reset.  Data: (XBC port << 44) | (XBC num << 32) | return status"

     --#SUMMARY "Error while copying the XBC routing to the local port"
     --#ARGUMENTS {}
     --#SEVERITY CRITICAL
     --#TIMEINDEX 100
     --#STATE OPERATIONAL
::= 8959


hpevtFabricCopyRdBackFailed TRAP-TYPE
     ENTERPRISE hpIpfE0Events
     VARIABLES { hpIpfEvtDetailStr }
     DESCRIPTION
        "The read immediately after a write while copying routing registers failed.  Data: whether or not the XBC Key was enabled"

     --#SUMMARY "A read after write of a XBC CSR failed"
     --#ARGUMENTS {}
     --#SEVERITY CRITICAL
     --#TIMEINDEX 100
     --#STATE OPERATIONAL
::= 8960


hpevtFabricRtgCompleteSm4RlsErr TRAP-TYPE
     ENTERPRISE hpIpfE0Events
     VARIABLES { hpIpfEvtDetailStr }
     DESCRIPTION
        "Failed to release a XBC Semaphore while marking each XBC in the complex to indicate that routing has completed.  Data: (XBC num << 32) | return value"

     --#SUMMARY "Couldn't release the Semaphore while writing routing states."
     --#ARGUMENTS {}
     --#SEVERITY WARNING
     --#TIMEINDEX 100
     --#STATE OPERATIONAL
::= 8962


hpevtFabricRtgCompleteWrFwdPrgErr TRAP-TYPE
     ENTERPRISE hpIpfE0Events
     VARIABLES { hpIpfEvtDetailStr }
     DESCRIPTION
        "Writing this XBC's forward progress register failed.  Data: (XBC num << 32) | return value"

     --#SUMMARY "Couldn't write the XBC's forward progress register"
     --#ARGUMENTS {}
     --#SEVERITY CRITICAL
     --#TIMEINDEX 100
     --#STATE OPERATIONAL
::= 8964


hpevtFabricRtgCompleteSm4AccessErr TRAP-TYPE
     ENTERPRISE hpIpfE0Events
     VARIABLES { hpIpfEvtDetailStr }
     DESCRIPTION
        "Failed to get a XBC Semaphore while marking each XBC in the complex to indicate that routing has completed.  Skipping this XBC.  Data: (XBC num << 32) | return value"

     --#SUMMARY "Couldn't access the XBC semaphore registers."
     --#ARGUMENTS {}
     --#SEVERITY CRITICAL
     --#TIMEINDEX 100
     --#STATE OPERATIONAL
::= 8965


hpevtFabricRtgCompleteTopologyErr TRAP-TYPE
     ENTERPRISE hpIpfE0Events
     VARIABLES { hpIpfEvtDetailStr }
     DESCRIPTION
        "Reading this XBC's topology register failed.    Data Field: (xbc num << 32) | return status"

     --#SUMMARY "Couldn't determine the complex fabric topology"
     --#ARGUMENTS {}
     --#SEVERITY CRITICAL
     --#TIMEINDEX 100
     --#STATE OPERATIONAL
::= 8966


hpevtFabricRouteTraversableCc2CcErr TRAP-TYPE
     ENTERPRISE hpIpfE0Events
     VARIABLES { hpIpfEvtDetailStr }
     DESCRIPTION
        "Could not check the traversability between two cells on an XBCless platform.  Data field: return status (1 = SUCCESS, 0 = FALSE, -1 = FAILURE)"

     --#SUMMARY "Error checking a cell to cell link during traversability tests"
     --#ARGUMENTS {}
     --#SEVERITY WARNING
     --#TIMEINDEX 100
     --#STATE OPERATIONAL
::= 8968


hpevtFabricDataRouteTraversableCc2CcErr TRAP-TYPE
     ENTERPRISE hpIpfE0Events
     VARIABLES { hpIpfEvtDetailStr }
     DESCRIPTION
        "Could not check the traversability between two cells on an XBCless platform.  Data field: return status (1 = SUCCESS, 0 = FALSE, -1 = FAILURE)"

     --#SUMMARY "An error occurred while traversing the cell to cell link."
     --#ARGUMENTS {}
     --#SEVERITY WARNING
     --#TIMEINDEX 100
     --#STATE OPERATIONAL
::= 8969


hpevtFabricCc2ccTraverseLclXinRdErr TRAP-TYPE
     ENTERPRISE hpIpfE0Events
     VARIABLES { hpIpfEvtDetailStr }
     DESCRIPTION
        "While checking traversability of a 2 cell back to back system, there was an error reading the local cell's XIN block.  Data Field: return status (1 or -1)"

     --#SUMMARY "Error reading the local cell's XIN link state"
     --#ARGUMENTS {}
     --#SEVERITY WARNING
     --#TIMEINDEX 100
     --#STATE OPERATIONAL
::= 8970


hpevtFabricCc2ccTraverseRmtXinRdErr TRAP-TYPE
     ENTERPRISE hpIpfE0Events
     VARIABLES { hpIpfEvtDetailStr }
     DESCRIPTION
        "While checking traversability of a 2 cell back to back system, there was an error reading the local cell's XIN block.  Data Field: return status (1 or -1)"

     --#SUMMARY "Error reading the remote cell's XIN link state register"
     --#ARGUMENTS {}
     --#SEVERITY WARNING
     --#TIMEINDEX 100
     --#STATE OPERATIONAL
::= 8971


hpevtFabricCc2ccTraverseLclNotInit TRAP-TYPE
     ENTERPRISE hpIpfE0Events
     VARIABLES { hpIpfEvtDetailStr }
     DESCRIPTION
        "Could not traverse to the target cell.  The XIN link is either not initialized, or is not connected to the target cell.  However, the target cell is designated to be within the partition.  Data Field: target cell << 56 | XIN link state register"

     --#SUMMARY "The XIN link is not connected to the target cell."
     --#ARGUMENTS {}
     --#SEVERITY WARNING
     --#TIMEINDEX 100
     --#STATE OPERATIONAL
::= 8972


hpevtFabricCc2ccTraverseRmtNotInit TRAP-TYPE
     ENTERPRISE hpIpfE0Events
     VARIABLES { hpIpfEvtDetailStr }
     DESCRIPTION
        "Could not traverse to the target cell.  The XIN link is either not initialized, or is not connected to the target cell.  However, the target cell is designated to be within the partition.  Data Field: target cell << 56 | XIN link state register"

     --#SUMMARY "The XIN link is not connected to the target cell."
     --#ARGUMENTS {}
     --#SEVERITY WARNING
     --#TIMEINDEX 100
     --#STATE OPERATIONAL
::= 8973


hpevtFabricDisableXinLinkReadErr TRAP-TYPE
     ENTERPRISE hpIpfE0Events
     VARIABLES { hpIpfEvtDetailStr }
     DESCRIPTION
        "Error reading the XIN_LINK_STATE register of the CC.  This occurred while verifying that the link had been disabled.  Data Field: cell being read << 56 | return status from the CSR read."

     --#SUMMARY "Error reading the XIN_LINK_STATE register while disabling the link"
     --#ARGUMENTS {}
     --#SEVERITY WARNING
     --#TIMEINDEX 100
     --#STATE OPERATIONAL
::= 8974


hpevtFabricXinInitRetryReadErr TRAP-TYPE
     ENTERPRISE hpIpfE0Events
     VARIABLES { hpIpfEvtDetailStr }
     DESCRIPTION
        "Failure while reading the XBC CSR containing the link status.  This occurred while attempting the retry process to get XBC to CC link initialized.  Data Field: link init status"

     --#SUMMARY "Error reading the XIN_LINK_STATE register"
     --#ARGUMENTS {}
     --#SEVERITY CRITICAL
     --#TIMEINDEX 100
     --#STATE OPERATIONAL
::= 8975


hpevtFabricAssertFabricCc TRAP-TYPE
     ENTERPRISE hpIpfE0Events
     VARIABLES { hpIpfEvtDetailStr }
     DESCRIPTION
        "An unexpected error occurred while initializing the fabric.  The firmware is not able to analyze this error.  Clues to the cause of this error may be found in the IPMI forward progress log (FPL) either shortly before or after this log entry occurred.  The FPL is available from the management processor using the 'sl' command.  HP-UX also saves these logs in the /var/stm/logs/os directory, and they can be viewed using the slview utility."

     --#SUMMARY "Unexpected fabric firmware error"
     --#ARGUMENTS {}
     --#SEVERITY WARNING
     --#TIMEINDEX 100
     --#STATE OPERATIONAL
::= 8976


hpevtCpuRestricted TRAP-TYPE
     ENTERPRISE hpIpfE0Events
     VARIABLES { hpIpfEvtDetailStr }
     DESCRIPTION
        "The CPU that just completed self tests is functionally or performace restricted.  The data field contains the Self Test State Parameter.  The 2-bit state field (bits 1..0) can have the following values when this event is displayed:
01 - Performance Restricted - cpu still functions
10 - Functionally Restricted - cpu doesn't function properly"

     --#SUMMARY "The CPU is performance or functionally restricted"
     --#ARGUMENTS {}
     --#SEVERITY WARNING
     --#TIMEINDEX 100
     --#STATE OPERATIONAL
::= 8979


hpevtPdhInvalidRtcCleared TRAP-TYPE
     ENTERPRISE hpIpfE0Events
     VARIABLES { hpIpfEvtDetailStr }
     DESCRIPTION
        "The RTC was found to be invalid and has been cleared"

     --#SUMMARY "The RTC was found to be invalid and has been cleared"
     --#ARGUMENTS {}
     --#SEVERITY WARNING
     --#TIMEINDEX 100
     --#STATE OPERATIONAL
::= 8981


hpevtLstNotRun TRAP-TYPE
     ENTERPRISE hpIpfE0Events
     VARIABLES { hpIpfEvtDetailStr }
     DESCRIPTION
        "System firmware requested that Late Self Tests be run by PAL, but PAL returned that the tests did not actually run on the processor.  The data field indicates the status word returned by PAL."

     --#SUMMARY "Status indicates that the Late Self Tests did not actually run"
     --#ARGUMENTS {}
     --#SEVERITY WARNING
     --#TIMEINDEX 100
     --#STATE OPERATIONAL
::= 8982


hpevtBootSetCellStateFabricFailure TRAP-TYPE
     ENTERPRISE hpIpfE0Events
     VARIABLES { hpIpfEvtDetailStr }
     DESCRIPTION
        "An attempt to update the cell state has failed due to a fabric crossbar failure.  The cell number being updated in in bits 63:56, while the traversable cell set (those cells connected to the fabric) is returned in bits 31:0"

     --#SUMMARY "A fabric walk failed while updating the cell state"
     --#ARGUMENTS {}
     --#SEVERITY CRITICAL
     --#TIMEINDEX 100
     --#STATE OPERATIONAL
::= 8983


hpevtBootResetCellStateFailure TRAP-TYPE
     ENTERPRISE hpIpfE0Events
     VARIABLES { hpIpfEvtDetailStr }
     DESCRIPTION
        "Failed to reset a cell due to an error setting the cell's state.  The cell will not be reset with the other cells in the PD.  The cell number is reported in the data field."

     --#SUMMARY "Could not reset the cell due to failure updating cell state"
     --#ARGUMENTS {}
     --#SEVERITY CRITICAL
     --#TIMEINDEX 100
     --#STATE OPERATIONAL
::= 8984


hpevtMemChipspareDeallocRank TRAP-TYPE
     ENTERPRISE hpIpfE0Events
     VARIABLES { hpIpfEvtDetailStr }
     DESCRIPTION
        "SFW has detected that a DRAM is failing on the DIMM specified by the physical location.  The rank the failing DIMM is part of will be deallocated."

     --#SUMMARY "DRAM failure on DIMM XX, deallocate rank"
     --#ARGUMENTS {}
     --#SEVERITY WARNING
     --#TIMEINDEX 100
     --#STATE OPERATIONAL
::= 9000


hpevtClockFreqError TRAP-TYPE
     ENTERPRISE hpIpfE0Events
     VARIABLES { hpIpfEvtDetailStr }
     DESCRIPTION
        "Internal CPU clocks are not valid when compared with the real time clock.  The data field contains the hex value of the elapsed time.  If this value is off a small percentage from the expected value (which is given in the next chassis code), the event is emitted."

     --#SUMMARY "System Clocks are not valid"
     --#ARGUMENTS {}
     --#SEVERITY CRITICAL
     --#TIMEINDEX 100
     --#STATE OPERATIONAL
::= 9019


hpevtFabricColaInitTraversableErr TRAP-TYPE
     ENTERPRISE hpIpfE0Events
     VARIABLES { hpIpfEvtDetailStr }
     DESCRIPTION
        "Could not traverse the fabric to the cell being added.  Data field: (chosen cell << 56) | return status, where -1 = failure"

     --#SUMMARY "Cell Online Addition failed due to fabric access error"
     --#ARGUMENTS {}
     --#SEVERITY CRITICAL
     --#TIMEINDEX 100
     --#STATE OPERATIONAL
::= 9020


hpevtFabricAttemptFocusedReroute TRAP-TYPE
     ENTERPRISE hpIpfE0Events
     VARIABLES { hpIpfEvtDetailStr }
     DESCRIPTION
        "A XBC port was found to be unhealthy on this reboot.  This cell will attempt to route around it. Data field: (local Cell << 56) | (local internal Port << 44) | (local XBC << 32) | XBC internal port number being routed around."

     --#SUMMARY "Fabric found a bad XBC port on a reboot.  Attempting to route around it."
     --#ARGUMENTS {}
     --#SEVERITY CRITICAL
     --#TIMEINDEX 100
     --#STATE OPERATIONAL
::= 9021


hpevtFabricCellRerouteNinfoErr TRAP-TYPE
     ENTERPRISE hpIpfE0Events
     VARIABLES { hpIpfEvtDetailStr }
     DESCRIPTION
        "Error getting the XBC port's expected neighbor from a firmware table.  Data field: 0 (SUCCESS) or -1 (FAILURE)"

     --#SUMMARY "Could not access an internal firmware table while rerouting XBC port"
     --#ARGUMENTS {}
     --#SEVERITY WARNING
     --#TIMEINDEX 100
     --#STATE OPERATIONAL
::= 9022


hpevtBootWakeCpuIsCpuDeconfigErr TRAP-TYPE
     ENTERPRISE hpIpfE0Events
     VARIABLES { hpIpfEvtDetailStr }
     DESCRIPTION
        "Either PDC is going to halt the cell or reset the partition because PDC was unable to access the PDH memory of either its local cell or another cell in the partition.  The data field contains the error return value from PDC function IsHCellCpuDeconfig()."

     --#SUMMARY "Cell/Partition to be reset because PDC couldn't read PDH memory"
     --#ARGUMENTS {}
     --#SEVERITY WARNING
     --#TIMEINDEX 100
     --#STATE OPERATIONAL
::= 9038


hpevtBootWakeCpuGetCountersErr TRAP-TYPE
     ENTERPRISE hpIpfE0Events
     VARIABLES { hpIpfEvtDetailStr }
     DESCRIPTION
        "Either PDC is going to halt the cell or reset the partition because PDC was unable to access the PDH memory of either its local cell or another cell in the partition.  The data field contains the error return value from PDC function SleepAndWakeupCountersGet()."

     --#SUMMARY "Cell/Partition to be reset because PDC couldn't read PDH memory"
     --#ARGUMENTS {}
     --#SEVERITY WARNING
     --#TIMEINDEX 100
     --#STATE OPERATIONAL
::= 9039


hpevtBootWakeCpuGetStructAddrErr TRAP-TYPE
     ENTERPRISE hpIpfE0Events
     VARIABLES { hpIpfEvtDetailStr }
     DESCRIPTION
        "Either PDC is going to halt the cell or reset the partition because PDC was unable to access the PDH memory of either its local cell or another cell in the partition.  The data field contains the error return value from PDC function PdhGetHCellStructAddr()."

     --#SUMMARY "Cell/Partition to be reset because PDC couldn't read PDH memory"
     --#ARGUMENTS {}
     --#SEVERITY WARNING
     --#TIMEINDEX 100
     --#STATE OPERATIONAL
::= 9040


hpevtBootCheckCpu4CompletionErr TRAP-TYPE
     ENTERPRISE hpIpfE0Events
     VARIABLES { hpIpfEvtDetailStr }
     DESCRIPTION
        "Either PDC is going to halt the cell or reset the partition because PDC was unable to access the PDH memory of either its local cell or another cell in the partition.  The data field contains the error return value from PDC function HasCpuCompletedWakeupTask()."

     --#SUMMARY "Cell/Partition to be reset because PDC couldn't read PDH memory"
     --#ARGUMENTS {}
     --#SEVERITY WARNING
     --#TIMEINDEX 100
     --#STATE OPERATIONAL
::= 9041


hpevtBootCheckCpuGetStructAddrErr TRAP-TYPE
     ENTERPRISE hpIpfE0Events
     VARIABLES { hpIpfEvtDetailStr }
     DESCRIPTION
        "Either PDC is going to halt the cell or reset the partition because PDC was unable to access the PDH memory of either its local cell or another cell in the partition.  The data field contains the error return value from PDC function PdhGetHCellStructAddr()."

     --#SUMMARY "Cell/Partition to be reset because PDC couldn't read PDH memory"
     --#ARGUMENTS {}
     --#SEVERITY WARNING
     --#TIMEINDEX 100
     --#STATE OPERATIONAL
::= 9042


hpevtReconfigResetScheduled TRAP-TYPE
     ENTERPRISE hpIpfE0Events
     VARIABLES { hpIpfEvtDetailStr }
     DESCRIPTION
        "There is a need to reset the cell for reconfiguration, but it cannot be done yet because the cell has not reported at BIB.  The Reset is being scheduled to be performed later."

     --#SUMMARY "A reset for reconfiguration will be performed soon on the cell."
     --#ARGUMENTS {}
     --#SEVERITY WARNING
     --#TIMEINDEX 100
     --#STATE OPERATIONAL
::= 9043


hpevtProfileWrongArchType TRAP-TYPE
     ENTERPRISE hpIpfE0Events
     VARIABLES { hpIpfEvtDetailStr }
     DESCRIPTION
        "When processing the complex profile, the an unexpected 'Architecture Type' was specified in the PA/IA Arch field.  The actual data found is displayed."

     --#SUMMARY "The Partition Profile specifies the wrong architecture type"
     --#ARGUMENTS {}
     --#SEVERITY WARNING
     --#TIMEINDEX 100
     --#STATE OPERATIONAL
::= 9045


hpevtBootCheckCpuIsDeconfigErr TRAP-TYPE
     ENTERPRISE hpIpfE0Events
     VARIABLES { hpIpfEvtDetailStr }
     DESCRIPTION
        "While trying to determine whether or not a particular processor has completed the task for which it was awakened, PDC was unable to access the deconfig byte information about the target processor.  A processor should always be able to access this data in PDH memory for any processor on its own cell and for any processor on a cell that is alive in the partition.  Therefore, PDC is either going to halt the cell or reset the partition because of this problem.  The data field contains the PDC error return status from IsHCellCpuDeconfig()."

     --#SUMMARY "Cell/Partition is about to be reset because PDC is unable to access CPU data"
     --#ARGUMENTS {}
     --#SEVERITY WARNING
     --#TIMEINDEX 100
     --#STATE OPERATIONAL
::= 9046


hpevtBootCheckCpuGetCountersErr TRAP-TYPE
     ENTERPRISE hpIpfE0Events
     VARIABLES { hpIpfEvtDetailStr }
     DESCRIPTION
        "While trying to determine whether or not a particular processor has completed the task for which it was awakened, PDC was unable to access the CPU's sleep and wakeup counters for the target processor.  A processor should always be able to access this data in PDH memory for any processor on its own cell and for any processor on a cell that is alive in the partition.  Therefore, PDC is either going to halt the cell or reset the partition because of this problem.  The data field contains the PDC error return status from SleepAndWakeupCountersGet()."

     --#SUMMARY "Cell/Partition is about to be reset because PDC is unable to access CPU data"
     --#ARGUMENTS {}
     --#SEVERITY WARNING
     --#TIMEINDEX 100
     --#STATE OPERATIONAL
::= 9047


hpevtBootPdMonarchRtnFromSwSetFpErr TRAP-TYPE
     ENTERPRISE hpIpfE0Events
     VARIABLES { hpIpfEvtDetailStr }
     DESCRIPTION
        "While trying to determine whether or not a particular processor has completed the task for which it was awakened, PDC was unable to access the CPU's forward progress state (ie PST state) for the target processor.  A processor should always be able to access this data in PDH memory for any processor on its own cell and for any processor on a cell that is alive in the partition.  Therefore, PDC is either going to halt the cell or reset the partition because of this problem.  The data field contains the PDC error return status from CpuFpSet()."

     --#SUMMARY "Cell/Partition about to be reset because PDC is unable to access CPU data"
     --#ARGUMENTS {}
     --#SEVERITY WARNING
     --#TIMEINDEX 100
     --#STATE OPERATIONAL
::= 9049


hpevtBootSlaveRtnFromFwSetFpErr TRAP-TYPE
     ENTERPRISE hpIpfE0Events
     VARIABLES { hpIpfEvtDetailStr }
     DESCRIPTION
        "While trying to determine whether or not a particular processor has completed the task for which it was awakened, PDC was unable to access the CPU's Forward Progress State (ie PST state) for the target processor.  A processor should always be able to access this data in PDH memory for any processor on its own cell and for any processor on a cell that is alive in the partition.  Therefore, PDC is either going to halt the cell or reset the partition because of this problem.  The data field contains the PDC error return status from CpuFpSet()."

     --#SUMMARY "Cell/Partition is about to be reset because PDC is unable to access CPU data"
     --#ARGUMENTS {}
     --#SEVERITY WARNING
     --#TIMEINDEX 100
     --#STATE OPERATIONAL
::= 9051


hpevtBootProblemBranchingToPgzLocation TRAP-TYPE
     ENTERPRISE hpIpfE0Events
     VARIABLES { hpIpfEvtDetailStr }
     DESCRIPTION
        "At a certain point in PDC boot, all of the processors in the partition except the PD monarch are put into a sleep, and they remain there until they are awakened by the PD monarch, at which time they read an architected location in Page Zero to find out where to branch to.  This gives the OS a mechanism by which to bring processors under its control and have it executing OS code.  This chassis log is sent if and when a problem is detected by PDC regarding the contents in the Page Zero location.  This means that PDC cannot branch to the location logged in the Page Zero location.  So, PDC sends this chassis log and then the processor returns to sleep.  The data field is unused."

     --#SUMMARY "PDC is unable to branch to other software via the Page Zero location"
     --#ARGUMENTS {}
     --#SEVERITY WARNING
     --#TIMEINDEX 100
     --#STATE OPERATIONAL
::= 9052


hpevtBootBadCpuOrder TRAP-TYPE
     ENTERPRISE hpIpfE0Events
     VARIABLES { hpIpfEvtDetailStr }
     DESCRIPTION
        "The Data Field contains the value used to determine a valid order."

     --#SUMMARY "New for MtWhatever: BOOT_BAD_CPU_ORDER"
     --#ARGUMENTS {}
     --#SEVERITY CRITICAL
     --#TIMEINDEX 100
     --#STATE OPERATIONAL
::= 9084


hpevtBootSlpWakeCntrsStructAddrErr TRAP-TYPE
     ENTERPRISE hpIpfE0Events
     VARIABLES { hpIpfEvtDetailStr }
     DESCRIPTION
        "While trying to get the sleep counter and the wakeup counter for a particular processor, which is kept in a data structure in PDH memory, PDC was unable to determine the address to the data structure on the remote cell.  PDC is supposed to be able to calculate addresses to anything in PDH memory on other cells in the partition.  The data field contains the PDC error return status from a function called PdhGetHCellStructAddr()."

     --#SUMMARY "PDC couldn't access a data structure in PDH memory"
     --#ARGUMENTS {}
     --#SEVERITY WARNING
     --#TIMEINDEX 100
     --#STATE OPERATIONAL
::= 9364


hpevtBootGetSleepTimeoutStructAddrErr TRAP-TYPE
     ENTERPRISE hpIpfE0Events
     VARIABLES { hpIpfEvtDetailStr }
     DESCRIPTION
        "Error occurred accessing a PDC data structure.  Depending upon the situation the cell or entire partition will be reset. 
 
The data field contains the return status for the function that encountered the error."

     --#SUMMARY "PDC couldn't access a data structure in PDH memory"
     --#ARGUMENTS {}
     --#SEVERITY WARNING
     --#TIMEINDEX 100
     --#STATE OPERATIONAL
::= 9365


hpevtBootMoveSlavesDispatcherAddrErr TRAP-TYPE
     ENTERPRISE hpIpfE0Events
     VARIABLES { hpIpfEvtDetailStr }
     DESCRIPTION
        "PDC is about to halt the cell because PDC was unable to determine the GNI address of the SlaveDispatcher function of PDC relocated to memory by PDC.  The data field contains the error return value from the function GetGniCodeAddrFromRomCodeAddr()."

     --#SUMMARY "Cell about to be halted because PDC couldn't determine relocated address of code"
     --#ARGUMENTS {}
     --#SEVERITY WARNING
     --#TIMEINDEX 100
     --#STATE OPERATIONAL
::= 9367


hpevtBootMoveSlavesCheckSlaveErr TRAP-TYPE
     ENTERPRISE hpIpfE0Events
     VARIABLES { hpIpfEvtDetailStr }
     DESCRIPTION
        "PDC is about to halt the cell because at least one of the processors didn't complete the task for which they were awakened and then return to sleep.  The data field contains an error return status."

     --#SUMMARY "Halting cell because a CPU didn't complete the task for which it was awakened"
     --#ARGUMENTS {}
     --#SEVERITY WARNING
     --#TIMEINDEX 100
     --#STATE OPERATIONAL
::= 9368


hpevtBootMoveSlavesFpSetAddrErr TRAP-TYPE
     ENTERPRISE hpIpfE0Events
     VARIABLES { hpIpfEvtDetailStr }
     DESCRIPTION
        "PDC is about to halt the cell because PDC was unable to determine the GNI address of the CpuFpSet() function of PDC relocated to memory by PDC.  The data field contains the error return value from the function GetGniCodeAddrFromRomCodeAddr()."

     --#SUMMARY "Cell about to be halted because PDC couldn't determine relocated address of code"
     --#ARGUMENTS {}
     --#SEVERITY WARNING
     --#TIMEINDEX 100
     --#STATE OPERATIONAL
::= 9370


hpevtBootMoveSlavesFpSetErr TRAP-TYPE
     ENTERPRISE hpIpfE0Events
     VARIABLES { hpIpfEvtDetailStr }
     DESCRIPTION
        "PDC is about to halt the cell because one or more of the slaves were unable to change their CPU FP state in PDH memory on the local cell.  The data field contains an error return status."

     --#SUMMARY "Cell about to be halted because CPU couldn't change its CPU FP (PST) state"
     --#ARGUMENTS {}
     --#SEVERITY WARNING
     --#TIMEINDEX 100
     --#STATE OPERATIONAL
::= 9371


hpevtBootMoveCellMonarchsStructAddrErr TRAP-TYPE
     ENTERPRISE hpIpfE0Events
     VARIABLES { hpIpfEvtDetailStr }
     DESCRIPTION
        "PDC was trying to move the cell monarchs on each of the non-core cells into the Dispatcher, but in order to do that, the PD monarch needs to be able to read the CPU number of the cell monarch on each of the non-core cells, which is kept in a data structure on each of the cells.  PDC was unable to get the address to the CELL_CPU_STATE structure in PDH memory in a cell in the partition.  The data field is the error return status from the PDC function called PdhGetHCellStructAddr()."

     --#SUMMARY "Partition about to be reset because PDC couldn't get address to a structure"
     --#ARGUMENTS {}
     --#SEVERITY CRITICAL
     --#TIMEINDEX 100
     --#STATE OPERATIONAL
::= 9372


hpevtBootMoveCellMonarchsCheckSlaveErr TRAP-TYPE
     ENTERPRISE hpIpfE0Events
     VARIABLES { hpIpfEvtDetailStr }
     DESCRIPTION
        "PDC is about to reset the partitionl because at least one of the processors didn't complete the task for which they were awakened and then return to sleep.  The data field contains the error return status from the PDC function CheckSingleSlave()."

     --#SUMMARY "Resetting a partition because a CPU didn't complete the task it was awakened for"
     --#ARGUMENTS {}
     --#SEVERITY CRITICAL
     --#TIMEINDEX 100
     --#STATE OPERATIONAL
::= 9373


hpevtBootMoveCellMonarchsFpSetAddrErr TRAP-TYPE
     ENTERPRISE hpIpfE0Events
     VARIABLES { hpIpfEvtDetailStr }
     DESCRIPTION
        "PDC is about to reset the partition because it is unable to determine the GNI address for the CpuFpSet() function for one or more of the cells in the partition.  The data field contains the error return status from GetGniCodeAddrFromRomCodeAddr()."

     --#SUMMARY "Resetting partition because PDC couldn't determine relocated address of code"
     --#ARGUMENTS {}
     --#SEVERITY CRITICAL
     --#TIMEINDEX 100
     --#STATE OPERATIONAL
::= 9375


hpevtBootMoveCellMonarchsFpSetErr TRAP-TYPE
     ENTERPRISE hpIpfE0Events
     VARIABLES { hpIpfEvtDetailStr }
     DESCRIPTION
        "PDC is about to reset the partition because one or more of the processors were unable to successfully modify their CPU FP State (aka their PST state).  The data field contains the error return status from the CpuFpSet() function."

     --#SUMMARY "Resetting partition because a CPU was unable to change its CPU FP state"
     --#ARGUMENTS {}
     --#SEVERITY CRITICAL
     --#TIMEINDEX 100
     --#STATE OPERATIONAL
::= 9376


hpevtBootDualCoreInitFail TRAP-TYPE
     ENTERPRISE hpIpfE0Events
     VARIABLES { hpIpfEvtDetailStr }
     DESCRIPTION
        "MX2 initialization failed."

     --#SUMMARY "CPU Dual Core Initialization Failed"
     --#ARGUMENTS {}
     --#SEVERITY WARNING
     --#TIMEINDEX 100
     --#STATE OPERATIONAL
::= 9379


hpevtBootDeconfigCpuModulePair TRAP-TYPE
     ENTERPRISE hpIpfE0Events
     VARIABLES { hpIpfEvtDetailStr }
     DESCRIPTION
        "A cpu that is attached to a cpu that is slated for deconfiguration is being deconfigured as well."

     --#SUMMARY "Second CPU in Pair has been disabled"
     --#ARGUMENTS {}
     --#SEVERITY WARNING
     --#TIMEINDEX 100
     --#STATE OPERATIONAL
::= 9380


hpevtBootVirtualizeDualCoreRegistersFail TRAP-TYPE
     ENTERPRISE hpIpfE0Events
     VARIABLES { hpIpfEvtDetailStr }
     DESCRIPTION
        "FW failed to virtualize the mx2 interposer."

     --#SUMMARY "Virtualzing Dual Core Registers Failed"
     --#ARGUMENTS {}
     --#SEVERITY CRITICAL
     --#TIMEINDEX 100
     --#STATE OPERATIONAL
::= 9382


hpevtBootVirtualizeDualCoreInterposerFail TRAP-TYPE
     ENTERPRISE hpIpfE0Events
     VARIABLES { hpIpfEvtDetailStr }
     DESCRIPTION
        "FW has failed to virtualize the mx2 interposer."

     --#SUMMARY "Virtualizing Dual Core Interposer has failed"
     --#ARGUMENTS {}
     --#SEVERITY WARNING
     --#TIMEINDEX 100
     --#STATE OPERATIONAL
::= 9383


hpevtBootInstallPmiHandlerFailed TRAP-TYPE
     ENTERPRISE hpIpfE0Events
     VARIABLES { hpIpfEvtDetailStr }
     DESCRIPTION
        "Installation of the FW PMI handler has failed."

     --#SUMMARY "Install PMI Handler Failed"
     --#ARGUMENTS {}
     --#SEVERITY CRITICAL
     --#TIMEINDEX 100
     --#STATE OPERATIONAL
::= 9385


hpevtPdhcCellIncompatable TRAP-TYPE
     ENTERPRISE hpIpfE0Events
     VARIABLES { hpIpfEvtDetailStr }
     DESCRIPTION
        "Cell and or cpus have failed compatability checks."

     --#SUMMARY "Cell failed compatability checks."
     --#ARGUMENTS {}
     --#SEVERITY CRITICAL
     --#TIMEINDEX 100
     --#STATE OPERATIONAL
::= 9388


hpevtPdhcPdhNotAvailable TRAP-TYPE
     ENTERPRISE hpIpfE0Events
     VARIABLES { hpIpfEvtDetailStr }
     DESCRIPTION
        "PDH space not available after release from reset."

     --#SUMMARY "PDH space not available after release from reset."
     --#ARGUMENTS {}
     --#SEVERITY CRITICAL
     --#TIMEINDEX 100
     --#STATE OPERATIONAL
::= 9389


hpevtPdhcMponFailed TRAP-TYPE
     ENTERPRISE hpIpfE0Events
     VARIABLES { hpIpfEvtDetailStr }
     DESCRIPTION
        "MPON failed to release."

     --#SUMMARY "MPON failed to release."
     --#ARGUMENTS {}
     --#SEVERITY CRITICAL
     --#TIMEINDEX 100
     --#STATE OPERATIONAL
::= 9390


hpevtPdhcDillonResetFailed TRAP-TYPE
     ENTERPRISE hpIpfE0Events
     VARIABLES { hpIpfEvtDetailStr }
     DESCRIPTION
        "Dillon failed to reset."

     --#SUMMARY "Dillon failed to reset."
     --#ARGUMENTS {}
     --#SEVERITY CRITICAL
     --#TIMEINDEX 100
     --#STATE OPERATIONAL
::= 9391


hpevtPdhcDmdClockFailed TRAP-TYPE
     ENTERPRISE hpIpfE0Events
     VARIABLES { hpIpfEvtDetailStr }
     DESCRIPTION
        "DMD clock is not running."

     --#SUMMARY "DMD clock is not running."
     --#ARGUMENTS {}
     --#SEVERITY CRITICAL
     --#TIMEINDEX 100
     --#STATE OPERATIONAL
::= 9392


hpevtAllCpusDeconfOnCell TRAP-TYPE
     ENTERPRISE hpIpfE0Events
     VARIABLES { hpIpfEvtDetailStr }
     DESCRIPTION
        "All possible CPUs on a cell have been scheduled for deconfiguration."

     --#SUMMARY "All cpus on the Cell are scheduled to be deconfigured"
     --#ARGUMENTS {}
     --#SEVERITY CRITICAL
     --#TIMEINDEX 100
     --#STATE OPERATIONAL
::= 9394


hpevtFabricLogRoutingRdErr TRAP-TYPE
     ENTERPRISE hpIpfE0Events
     VARIABLES { hpIpfEvtDetailStr }
     DESCRIPTION
        "A read error occurred while dumping the XBC port routing registers during boot.  This cell will attempt fabricless boot.  Data field: (XBC port << 48) | (XBC num << 32) | error status reg"

     --#SUMMARY "A read error occurred while dumping the routing registers"
     --#ARGUMENTS {}
     --#SEVERITY CRITICAL
     --#TIMEINDEX 100
     --#STATE OPERATIONAL
::= 9403


hpevtFabricLinkRendezDisableErr TRAP-TYPE
     ENTERPRISE hpIpfE0Events
     VARIABLES { hpIpfEvtDetailStr }
     DESCRIPTION
        "After cell rendezvous for a 2 cell Medel, only one cell made it into the partition.  Disabling the link failed.  The cell will reset for reconfig.  Data Field: return status"

     --#SUMMARY "Failed to disable the CC to CC link"
     --#ARGUMENTS {}
     --#SEVERITY CRITICAL
     --#TIMEINDEX 100
     --#STATE OPERATIONAL
::= 9412


hpevtAcDeletedA0 TRAP-TYPE
     ENTERPRISE hpIpfE0Events
     VARIABLES { hpIpfEvtDetailStr }
     DESCRIPTION
        "Power is no longer being supplied to input A0 on the cabinet specified in the data field."

     --#SUMMARY "Power has been removed from AC input A0."
     --#ARGUMENTS {}
     --#SEVERITY WARNING
     --#TIMEINDEX 100
     --#STATE OPERATIONAL
::= 9417


hpevtAcDeletedA1 TRAP-TYPE
     ENTERPRISE hpIpfE0Events
     VARIABLES { hpIpfEvtDetailStr }
     DESCRIPTION
        "Power is no longer being supplied to input A1 on the cabinet specified in the data field."

     --#SUMMARY "Power has been removed from AC input A1."
     --#ARGUMENTS {}
     --#SEVERITY WARNING
     --#TIMEINDEX 100
     --#STATE OPERATIONAL
::= 9418


hpevtAcDeletedB0 TRAP-TYPE
     ENTERPRISE hpIpfE0Events
     VARIABLES { hpIpfEvtDetailStr }
     DESCRIPTION
        "Power is no longer being supplied to input B0 on the cabinet specified in the data field."

     --#SUMMARY "Power has been removed from AC input B0."
     --#ARGUMENTS {}
     --#SEVERITY WARNING
     --#TIMEINDEX 100
     --#STATE OPERATIONAL
::= 9419


hpevtAcDeletedB1 TRAP-TYPE
     ENTERPRISE hpIpfE0Events
     VARIABLES { hpIpfEvtDetailStr }
     DESCRIPTION
        "Power is no longer being supplied to input B1 on the cabinet specified in the data field."

     --#SUMMARY "Power has been removed from AC input B1."
     --#ARGUMENTS {}
     --#SEVERITY WARNING
     --#TIMEINDEX 100
     --#STATE OPERATIONAL
::= 9420


hpevtFabricCc2CcLinkDisableErr TRAP-TYPE
     ENTERPRISE hpIpfE0Events
     VARIABLES { hpIpfEvtDetailStr }
     DESCRIPTION
        "Failed to disable the XIN link init CSR on a XBCless system.  Cell will halt.  Data field: return status (0 = SUCCESS, -1 = FAILURE), -1 is expected for this event."

     --#SUMMARY "Failed to disable the XIN link during a failed link init"
     --#ARGUMENTS {}
     --#SEVERITY WARNING
     --#TIMEINDEX 100
     --#STATE OPERATIONAL
::= 9428


hpevtFabricISREarlyCopyRoutingErr TRAP-TYPE
     ENTERPRISE hpIpfE0Events
     VARIABLES { hpIpfEvtDetailStr }
     DESCRIPTION
        "Error writing the XBC port's routing registers.  The cell will reboot.  Data Field: XBC port << 44 | XBC num << 32 | return status"

     --#SUMMARY "Error copying the routing registers to the local port"
     --#ARGUMENTS {}
     --#SEVERITY CRITICAL
     --#TIMEINDEX 100
     --#STATE OPERATIONAL
::= 9430


hpevtFabricClrLinkInitBitErrMaskRd TRAP-TYPE
     ENTERPRISE hpIpfE0Events
     VARIABLES { hpIpfEvtDetailStr }
     DESCRIPTION
        "Could not read the XIN error mask regisiter on the CC.  Data Field: cell number and return status"

     --#SUMMARY "Error while reading the remote CC's XIN Error Mask register"
     --#ARGUMENTS {}
     --#SEVERITY WARNING
     --#TIMEINDEX 100
     --#STATE OPERATIONAL
::= 9431


hpevtFabricClrLinkInitBitErrMaskWr TRAP-TYPE
     ENTERPRISE hpIpfE0Events
     VARIABLES { hpIpfEvtDetailStr }
     DESCRIPTION
        "Could not write the XIN error mask regisiter on the CC.  Data Field: cell number and return status"

     --#SUMMARY "Error clearing the init packet received bit in the XIN error mask"
     --#ARGUMENTS {}
     --#SEVERITY WARNING
     --#TIMEINDEX 100
     --#STATE OPERATIONAL
::= 9432


hpevtFabricPortPairRdPstatusErr TRAP-TYPE
     ENTERPRISE hpIpfE0Events
     VARIABLES { hpIpfEvtDetailStr }
     DESCRIPTION
        "While testing link traversability, a XBC CSR could not be read.  Data Field: Port Number << 44 | XBC Number << 32 | return value"

     --#SUMMARY "Failed to read the XBC's Port Status register"
     --#ARGUMENTS {}
     --#SEVERITY WARNING
     --#TIMEINDEX 100
     --#STATE OPERATIONAL
::= 9433


hpevtPdhBatteryPowerLow TRAP-TYPE
     ENTERPRISE hpIpfE0Events
     VARIABLES { hpIpfEvtDetailStr }
     DESCRIPTION
        "The Battery-Low interrupt was signaled in the Interrupt Pending Register in Dillon (PDH) by the hardware.  PDHC is merely reporting the problem."

     --#SUMMARY "PDHC has detected the PDH battery low warning."
     --#ARGUMENTS {}
     --#SEVERITY WARNING
     --#TIMEINDEX 100
     --#STATE OPERATIONAL
::= 9438


hpevtNoHandoffToOsMca TRAP-TYPE
     ENTERPRISE hpIpfE0Events
     VARIABLES { hpIpfEvtDetailStr }
     DESCRIPTION
        "This means that the system FW MCA handler is not going to handoff to the OS_MCA handler."

     --#SUMMARY "FW will not handoff to the OS_MCA handler for this MCA event"
     --#ARGUMENTS {}
     --#SEVERITY CRITICAL
     --#TIMEINDEX 100
     --#STATE OPERATIONAL
::= 9440


hpevtBootRtnFromSwCantGetCounters TRAP-TYPE
     ENTERPRISE hpIpfE0Events
     VARIABLES { hpIpfEvtDetailStr }
     DESCRIPTION
        "When returning from other software, like when returning from ISL, PDC is trying to make sure that all of the slave processors in the partition are asleep; however, this event ID indicates that we were unable to access PDH memory of a cell that is supposed to be part of our partition.  The data field contains the error return status from a function called SleepAndWakeupCountersGet()."

     --#SUMMARY "Resetting the partition because couldn't access PDH memory"
     --#ARGUMENTS {}
     --#SEVERITY CRITICAL
     --#TIMEINDEX 100
     --#STATE OPERATIONAL
::= 9441


hpevtBootRtnFromSwCpuNotAsleep TRAP-TYPE
     ENTERPRISE hpIpfE0Events
     VARIABLES { hpIpfEvtDetailStr }
     DESCRIPTION
        "When returning to PDC from other software, like returning from ISL, PDC tries to verify that all the slave processors are in the expected state (ie that all slave processors are asleep); however, this event ID indicates that at least one processor active in the partition was not asleep.  So, PDC is going to reset the partition.  The data field of this Event ID is the global CPU number of the first CPU in the partition not found in the expected state."

     --#SUMMARY "Resetting the partition because a processor was not in expected state"
     --#ARGUMENTS {}
     --#SEVERITY CRITICAL
     --#TIMEINDEX 100
     --#STATE OPERATIONAL
::= 9442


hpevtBootDeconfigAbsentCantSetCpuState TRAP-TYPE
     ENTERPRISE hpIpfE0Events
     VARIABLES { hpIpfEvtDetailStr }
     DESCRIPTION
        "PDC could not access one of its own data structures on the local cell.  The cell will be halted. 
 
The data field contains the return status from the PDC function that encountered the error."

     --#SUMMARY "Halting the cell because a cell couldn't access its own PDH memory"
     --#ARGUMENTS {}
     --#SEVERITY WARNING
     --#TIMEINDEX 100
     --#STATE OPERATIONAL
::= 9445


hpevtNvramBlockTableCorrupt TRAP-TYPE
     ENTERPRISE hpIpfE0Events
     VARIABLES { hpIpfEvtDetailStr }
     DESCRIPTION
        "The NVRAM-based descriptor for System Firmware NVRAM blocks is corrupt."

     --#SUMMARY "The NVRAM block table maintained by System Firmware is corrupt"
     --#ARGUMENTS {}
     --#SEVERITY CRITICAL
     --#TIMEINDEX 100
     --#STATE OPERATIONAL
::= 9448


hpevtBootMoveSlavesSetTimeoutErr TRAP-TYPE
     ENTERPRISE hpIpfE0Events
     VARIABLES { hpIpfEvtDetailStr }
     DESCRIPTION
        "The cell will be reset because it was unable to access PDH memory on its own cell.  While trying to move all the slave processors on the cell to the 'late boot sleep', the monarch tried to write the sleep timeout to PDH memory on its own cell, but encountered an error in doing so.  The data field contains a PDC return status."

     --#SUMMARY "Resetting cell because processor couldn't access it's own PDH memory"
     --#ARGUMENTS {}
     --#SEVERITY WARNING
     --#TIMEINDEX 100
     --#STATE OPERATIONAL
::= 9450


hpevtBootReconfigAllCpus TRAP-TYPE
     ENTERPRISE hpIpfE0Events
     VARIABLES { hpIpfEvtDetailStr }
     DESCRIPTION
        "All CPUs have been determined to be manually deconfigured in NVM during boot.  This may only happen when switching from single core CPU deconfiguration to multi-core CPU deconfiguration in product qualification testing.  As a recovery, NVM settings have been changed to reconfigure all CPUs."

     --#SUMMARY "All CPUs were deconfigured and have now been reconfigured."
     --#ARGUMENTS {}
     --#SEVERITY WARNING
     --#TIMEINDEX 100
     --#STATE OPERATIONAL
::= 9460


hpevtBootGetNumcoresFailure TRAP-TYPE
     ENTERPRISE hpIpfE0Events
     VARIABLES { hpIpfEvtDetailStr }
     DESCRIPTION
        "A failure has occurred trying to determine the number of CPU cores per module.  Depending upon the situation, either the cell will be halted or the entire partition will be reset."

     --#SUMMARY "A failure has occurred trying to get the number of CPU cores per module."
     --#ARGUMENTS {}
     --#SEVERITY WARNING
     --#TIMEINDEX 100
     --#STATE OPERATIONAL
::= 9461


hpevtFabricRmtRoutePortTopoErr TRAP-TYPE
     ENTERPRISE hpIpfE0Events
     VARIABLES { hpIpfEvtDetailStr }
     DESCRIPTION
        "While writing the remote routing, the local XBC could not be accessed to determine the topology.  Look for additional chassis codes to determine what will happen as a result of this failure.  Data field: return status, either SUCCESS (0) or (-1)"

     --#SUMMARY "Couldn't read the topology from the XBC register"
     --#ARGUMENTS {}
     --#SEVERITY WARNING
     --#TIMEINDEX 100
     --#STATE OPERATIONAL
::= 9465


hpevtFabricCellRerouteFailure TRAP-TYPE
     ENTERPRISE hpIpfE0Events
     VARIABLES { hpIpfEvtDetailStr }
     DESCRIPTION
        "Failed to route around a broken link on cell reboot.  Data Field: PDC return status"

     --#SUMMARY "Attempt to update Cell Static Routing has failed"
     --#ARGUMENTS {}
     --#SEVERITY CRITICAL
     --#TIMEINDEX 100
     --#STATE OPERATIONAL
::= 9466


hpevtFabricRdFailedLinksError TRAP-TYPE
     ENTERPRISE hpIpfE0Events
     VARIABLES { hpIpfEvtDetailStr }
     DESCRIPTION
        "Could not read the XBC register that contains the number of links that are currently broken on the complex.  Data Field: (XBC Num << 32) | PDC return status"

     --#SUMMARY "Failed to read the XBC CSR that contains the number of failed links"
     --#ARGUMENTS {}
     --#SEVERITY WARNING
     --#TIMEINDEX 100
     --#STATE OPERATIONAL
::= 9468


hpevtFabricWrFailedLinksRdError TRAP-TYPE
     ENTERPRISE hpIpfE0Events
     VARIABLES { hpIpfEvtDetailStr }
     DESCRIPTION
        "Could not read the XBC register that contains the number of links that are currently broken on the complex.  Data Field: (XBC Num << 32) | PDC return status"

     --#SUMMARY "Failed to read the XBC CSR that contains the number of failed links"
     --#ARGUMENTS {}
     --#SEVERITY WARNING
     --#TIMEINDEX 100
     --#STATE OPERATIONAL
::= 9469


hpevtFabricWrFailedLinksWrError TRAP-TYPE
     ENTERPRISE hpIpfE0Events
     VARIABLES { hpIpfEvtDetailStr }
     DESCRIPTION
        "Could not write the XBC register that contains the number of links that are currently broken on the complex.  Data Field: (XBC Num << 32) | PDC return status"

     --#SUMMARY "Failed to write the XBC CSR that contains the number of failed links"
     --#ARGUMENTS {}
     --#SEVERITY WARNING
     --#TIMEINDEX 100
     --#STATE OPERATIONAL
::= 9470


hpevtFabricIncFailedLinksRdError TRAP-TYPE
     ENTERPRISE hpIpfE0Events
     VARIABLES { hpIpfEvtDetailStr }
     DESCRIPTION
        "Could not read the XBC register that contains the number of links that are currently broken on the complex.  Data Field: (XBC Num << 32) | PDC return status"

     --#SUMMARY "Failed to read the XBC CSR that contains the number of failed links"
     --#ARGUMENTS {}
     --#SEVERITY CRITICAL
     --#TIMEINDEX 100
     --#STATE OPERATIONAL
::= 9471


hpevtFabricIncFailedLinksWrError TRAP-TYPE
     ENTERPRISE hpIpfE0Events
     VARIABLES { hpIpfEvtDetailStr }
     DESCRIPTION
        "Could not write the XBC register that contains the number of links that are currently broken on the complex.  Data Field: (XBC Num << 32) | PDC return status"

     --#SUMMARY "Failed to write the XBC CSR that contains the number of failed links"
     --#ARGUMENTS {}
     --#SEVERITY CRITICAL
     --#TIMEINDEX 100
     --#STATE OPERATIONAL
::= 9472


hpevtFabricIncFailedLinksHitLimit TRAP-TYPE
     ENTERPRISE hpIpfE0Events
     VARIABLES { hpIpfEvtDetailStr }
     DESCRIPTION
        "Too many broken crossbar links were found.  This cell will have no connectivity to other cells in the complex.  It will attempt a fabricless boot, except in a few configurations.  Data Field: (XBC Num << 32) | number of broken links"

     --#SUMMARY "This cell encountered too many broken crossbar links"
     --#ARGUMENTS {}
     --#SEVERITY CRITICAL
     --#TIMEINDEX 100
     --#STATE OPERATIONAL
::= 9473


hpevtFabricRtgCompleteRdFldLinksErr TRAP-TYPE
     ENTERPRISE hpIpfE0Events
     VARIABLES { hpIpfEvtDetailStr }
     DESCRIPTION
        "Could not read the XBC register that contains the number of links that are currently broken on the complex.  Data Field:  PDC return status"

     --#SUMMARY "Failed to read the XBC CSR that contains the number of failed links"
     --#ARGUMENTS {}
     --#SEVERITY CRITICAL
     --#TIMEINDEX 100
     --#STATE OPERATIONAL
::= 9474


hpevtFabricRtgCompleteWrFldLinksErr TRAP-TYPE
     ENTERPRISE hpIpfE0Events
     VARIABLES { hpIpfEvtDetailStr }
     DESCRIPTION
        "Could not write the XBC register that contains the number of links that are currently broken on the complex.  Data Field: (XBC Num << 32) | PDC return status"

     --#SUMMARY "Failed to write the XBC CSR that contains the number of failed links"
     --#ARGUMENTS {}
     --#SEVERITY CRITICAL
     --#TIMEINDEX 100
     --#STATE OPERATIONAL
::= 9475


hpevtFabricCellRerouteRdXbcErr TRAP-TYPE
     ENTERPRISE hpIpfE0Events
     VARIABLES { hpIpfEvtDetailStr }
     DESCRIPTION
        "Could not read the XBC register that marks the ports that have been routed around.  Data Field: (XBC Num << 32) | PDC return status"

     --#SUMMARY "Failed to read the XBC CSR that marks the port route arounds"
     --#ARGUMENTS {}
     --#SEVERITY CRITICAL
     --#TIMEINDEX 100
     --#STATE OPERATIONAL
::= 9476


hpevtFabricCellRerouteNbrNotReachable TRAP-TYPE
     ENTERPRISE hpIpfE0Events
     VARIABLES { hpIpfEvtDetailStr }
     DESCRIPTION
        "The PIOB route to the remote XBC was not traversable.  The cell will halt.  Data Field: (XBC Num << 32) | PDC return status"

     --#SUMMARY "Could not traverse the PIOB route to the remote XBC"
     --#ARGUMENTS {}
     --#SEVERITY CRITICAL
     --#TIMEINDEX 100
     --#STATE OPERATIONAL
::= 9477


hpevtFabricCellRerouteSm4RlsErr TRAP-TYPE
     ENTERPRISE hpIpfE0Events
     VARIABLES { hpIpfEvtDetailStr }
     DESCRIPTION
        "Could not release the remote XBC's semaphore.  Cell will halt.  Data Field: (XBC Num << 32) | PDC return status"

     --#SUMMARY "Failed to release the XBC semaphore after landmining a remote XBC port"
     --#ARGUMENTS {}
     --#SEVERITY WARNING
     --#TIMEINDEX 100
     --#STATE OPERATIONAL
::= 9479


hpevtFabricRmtRoutePortBcastWrErr TRAP-TYPE
     ENTERPRISE hpIpfE0Events
     VARIABLES { hpIpfEvtDetailStr }
     DESCRIPTION
        "Failed to complete a broadcast write to an XBC.  Data Field: (XBC Num << 32) | PDC return status"

     --#SUMMARY "Failed to do a broadcast write to the XBC Remote Routing registers"
     --#ARGUMENTS {}
     --#SEVERITY WARNING
     --#TIMEINDEX 100
     --#STATE OPERATIONAL
::= 9480


hpevtFabricRmtRoutePortRdErr TRAP-TYPE
     ENTERPRISE hpIpfE0Events
     VARIABLES { hpIpfEvtDetailStr }
     DESCRIPTION
        "Failed to complete a read to the built-in port of a XBC.  Data Field: (XBC Num << 32) | PDC return status"

     --#SUMMARY "Failed to read a XBC Remote Routing register"
     --#ARGUMENTS {}
     --#SEVERITY WARNING
     --#TIMEINDEX 100
     --#STATE OPERATIONAL
::= 9481


hpevtFabricRmtRoutePortWrErr TRAP-TYPE
     ENTERPRISE hpIpfE0Events
     VARIABLES { hpIpfEvtDetailStr }
     DESCRIPTION
        "Failed to complete a write to the local cell's port of the XBC.  Data Field: (XBC Port << 44) | (XBC Num << 32) | PDC return status"

     --#SUMMARY "Failed to write a XBC Remote Routing register"
     --#ARGUMENTS {}
     --#SEVERITY WARNING
     --#TIMEINDEX 100
     --#STATE OPERATIONAL
::= 9482


hpevtIoLinkSubsystemFailed TRAP-TYPE
     ENTERPRISE hpIpfE0Events
     VARIABLES { hpIpfEvtDetailStr }
     DESCRIPTION
        "The link between the CC and SBA failed meaning that I/O is not available to the reporting cell."

     --#SUMMARY "The link between the CC and SBA failed"
     --#ARGUMENTS {}
     --#SEVERITY CRITICAL
     --#TIMEINDEX 100
     --#STATE OPERATIONAL
::= 9484


hpevtIoSbaSubsystemFailed TRAP-TYPE
     ENTERPRISE hpIpfE0Events
     VARIABLES { hpIpfEvtDetailStr }
     DESCRIPTION
        "An error was detected in the SBA and the reporting cell has no I/O."

     --#SUMMARY "The SBA failed and the cell has no I/O"
     --#ARGUMENTS {}
     --#SEVERITY CRITICAL
     --#TIMEINDEX 100
     --#STATE OPERATIONAL
::= 9485


hpevtIoErrengineError TRAP-TYPE
     ENTERPRISE hpIpfE0Events
     VARIABLES { hpIpfEvtDetailStr }
     DESCRIPTION
        "The structured exception handling within the system firmware failed during I/O initialization."

     --#SUMMARY "The system firmware had an error with the structured error handling mechanism."
     --#ARGUMENTS {}
     --#SEVERITY CRITICAL
     --#TIMEINDEX 100
     --#STATE OPERATIONAL
::= 9486


hpevtIoDiscEeMallocErr TRAP-TYPE
     ENTERPRISE hpIpfE0Events
     VARIABLES { hpIpfEvtDetailStr }
     DESCRIPTION
        "There is not enough malloc resources for the I/O structure exception handling.  I/O on the reported cell is not available."

     --#SUMMARY "Not enough malloc resources for I/O structure error handlig."
     --#ARGUMENTS {}
     --#SEVERITY CRITICAL
     --#TIMEINDEX 100
     --#STATE OPERATIONAL
::= 9487


hpevtIoDiscEeCreatetreeErr TRAP-TYPE
     ENTERPRISE hpIpfE0Events
     VARIABLES { hpIpfEvtDetailStr }
     DESCRIPTION
        "Error creating the structure for housing the I/O structured exception handling services and data.  I/O is lost on the reporting cell."

     --#SUMMARY "Unable to create entry for I/O structure error handling."
     --#ARGUMENTS {}
     --#SEVERITY CRITICAL
     --#TIMEINDEX 100
     --#STATE OPERATIONAL
::= 9488


hpevtIoDiscEeAttachserviceErr TRAP-TYPE
     ENTERPRISE hpIpfE0Events
     VARIABLES { hpIpfEvtDetailStr }
     DESCRIPTION
        "Unable to bind the I/O structure exception handling to the internal data structures."

     --#SUMMARY "Unable to bind services for I/O structure exception handling."
     --#ARGUMENTS {}
     --#SEVERITY CRITICAL
     --#TIMEINDEX 100
     --#STATE OPERATIONAL
::= 9489


hpevtIoDiscEeInitErr TRAP-TYPE
     ENTERPRISE hpIpfE0Events
     VARIABLES { hpIpfEvtDetailStr }
     DESCRIPTION
        "Error detected while initializing the I/O structure exception handling services."

     --#SUMMARY "Error initializing the I/O structure exception handling services."
     --#ARGUMENTS {}
     --#SEVERITY CRITICAL
     --#TIMEINDEX 100
     --#STATE OPERATIONAL
::= 9490


hpevtIoDiscEeInitializationErr TRAP-TYPE
     ENTERPRISE hpIpfE0Events
     VARIABLES { hpIpfEvtDetailStr }
     DESCRIPTION
        "Error initializing the I/O structure exception handling data structures."

     --#SUMMARY "Error initializing structured I/O exception data structures."
     --#ARGUMENTS {}
     --#SEVERITY CRITICAL
     --#TIMEINDEX 100
     --#STATE OPERATIONAL
::= 9491


hpevtIoDiscEeContextErr TRAP-TYPE
     ENTERPRISE hpIpfE0Events
     VARIABLES { hpIpfEvtDetailStr }
     DESCRIPTION
        "The structured I/O exception handling data structures have an error.  All I/O on the reporting cell is not available."

     --#SUMMARY "The I/O exception context has an error."
     --#ARGUMENTS {}
     --#SEVERITY CRITICAL
     --#TIMEINDEX 100
     --#STATE OPERATIONAL
::= 9492


hpevtIoDiscCreateSbaNodeErr TRAP-TYPE
     ENTERPRISE hpIpfE0Events
     VARIABLES { hpIpfEvtDetailStr }
     DESCRIPTION
        "While setting up the internal SBA data and service an error was detected.  All I/O for the reporting cell is not available."

     --#SUMMARY "Error creating the internal data and services for the SBA."
     --#ARGUMENTS {}
     --#SEVERITY CRITICAL
     --#TIMEINDEX 100
     --#STATE OPERATIONAL
::= 9493


hpevtIoDiscSbaAttachserviceErr TRAP-TYPE
     ENTERPRISE hpIpfE0Events
     VARIABLES { hpIpfEvtDetailStr }
     DESCRIPTION
        "An error attaching firmware services to the internal structures was detected.  All I/O on the reporting cell is not available."

     --#SUMMARY "Error attaching the services to the SBA internal data structures."
     --#ARGUMENTS {}
     --#SEVERITY CRITICAL
     --#TIMEINDEX 100
     --#STATE OPERATIONAL
::= 9494


hpevtIoDiscSbaInitnodeErr TRAP-TYPE
     ENTERPRISE hpIpfE0Events
     VARIABLES { hpIpfEvtDetailStr }
     DESCRIPTION
        "System firmware detected an error initializing internal SBA data structures and services.  This is usually an error with unavailable resources."

     --#SUMMARY "Error initializing the internal SBA data and services."
     --#ARGUMENTS {}
     --#SEVERITY CRITICAL
     --#TIMEINDEX 100
     --#STATE OPERATIONAL
::= 9495


hpevtIoDiscSbaUnknownErr TRAP-TYPE
     ENTERPRISE hpIpfE0Events
     VARIABLES { hpIpfEvtDetailStr }
     DESCRIPTION
        "The SBA type is unknown to the system firmware.  The I/O on the reporting cell is not available."

     --#SUMMARY "The SBA type is unknown to the system firmware"
     --#ARGUMENTS {}
     --#SEVERITY CRITICAL
     --#TIMEINDEX 100
     --#STATE OPERATIONAL
::= 9496


hpevtIoDeviceMissing TRAP-TYPE
     ENTERPRISE hpIpfE0Events
     VARIABLES { hpIpfEvtDetailStr }
     DESCRIPTION
        "An expected I/O device cannot be detected by the system firmware."

     --#SUMMARY "An embedded I/O device is missing."
     --#ARGUMENTS {}
     --#SEVERITY WARNING
     --#TIMEINDEX 100
     --#STATE OPERATIONAL
::= 9497


hpevtFabricRmtRoutePortBadReroute TRAP-TYPE
     ENTERPRISE hpIpfE0Events
     VARIABLES { hpIpfEvtDetailStr }
     DESCRIPTION
        " Too many broken links!  The XBC port route around failed because the route-around port was bad too.  Data field: (XBC port << 44) | (XBC num << 32) | port state"

     --#SUMMARY "Fabric link route around failed because the route around port was bad"
     --#ARGUMENTS {}
     --#SEVERITY WARNING
     --#TIMEINDEX 100
     --#STATE OPERATIONAL
::= 9498


hpevtAgtPredictMemFail TRAP-TYPE
     ENTERPRISE hpIpfE0Events
     VARIABLES { hpIpfEvtDetailStr }
     DESCRIPTION
        "ECC (Error Checking and Correcting) memory is designed to detect and correct single-bit errors that occasionally occur in computer systems.  This memory module is currently correcting many single bit errors."

     --#SUMMARY "Predictive Failure in Memory"
     --#ARGUMENTS {}
     --#SEVERITY WARNING
     --#TIMEINDEX 100
     --#STATE OPERATIONAL
::= 9652


hpevtWinAgtLockedProperty TRAP-TYPE
     ENTERPRISE hpIpfE0Events
     VARIABLES { hpIpfEvtDetailStr }
     DESCRIPTION
        "Server Agents SNMP branch is not responding due to a portion of the IPMI Management Subsystem being locked by another entity."

     --#SUMMARY "Windows: Server Agents Management data not accessible, locked property"
     --#ARGUMENTS {}
     --#SEVERITY WARNING
     --#TIMEINDEX 100
     --#STATE OPERATIONAL
::= 9653


hpevtIoPciPowerOverloadErr TRAP-TYPE
     ENTERPRISE hpIpfE0Events
     VARIABLES { hpIpfEvtDetailStr }
     DESCRIPTION
        "A non-hot plug I/O slot's power consumption increases the total I/O power consumption beyond the supported limit.  Firmware will display the following EFI error message, 'I/O configuration exceeds power limit' and disallow O/S boot. 
Data Field: Physical location of the I/O slot."

     --#SUMMARY "PCI slot exceeds power limit"
     --#ARGUMENTS {}
     --#SEVERITY CRITICAL
     --#TIMEINDEX 100
     --#STATE OPERATIONAL
::= 9658


hpevtMemSbeSeedingEnabled TRAP-TYPE
     ENTERPRISE hpIpfE0Events
     VARIABLES { hpIpfEvtDetailStr }
     DESCRIPTION
        "This is a warning that the system is running in a degregated mode.   It will only be emitted in MFG mode when Memory SBE Seeding is enabled.  This is only for testing of SBE seeding for LAB and possibly MFG use ONLY.  It should NEVER be seen in the field."

     --#SUMMARY "(warning) Outputted in MFG, when Memory SBE Seeding is enabled"
     --#ARGUMENTS {}
     --#SEVERITY WARNING
     --#TIMEINDEX 100
     --#STATE OPERATIONAL
::= 9659


hpevtFabricWrFailedLinksTopoErr TRAP-TYPE
     ENTERPRISE hpIpfE0Events
     VARIABLES { hpIpfEvtDetailStr }
     DESCRIPTION
        "Read failure while writing the number of failed links to the XBC.  Data Field: Return Status (SUCCESS = 0, FAILURE = -1)"

     --#SUMMARY "Failed to read the fabric topology information from the XBC"
     --#ARGUMENTS {}
     --#SEVERITY CRITICAL
     --#TIMEINDEX 100
     --#STATE OPERATIONAL
::= 9661


hpevtBootErrInitGroupCPaFields TRAP-TYPE
     ENTERPRISE hpIpfE0Events
     VARIABLES { hpIpfEvtDetailStr }
     DESCRIPTION
        "PDC could not access a complex profile.  The partition will be reset because the available complex profile is not valid. 
 
Data field contains the return status from the function that encountered the error."

     --#SUMMARY "PDC failed to initalize PA specific fields of group C after finding IA bit set."
     --#ARGUMENTS {}
     --#SEVERITY CRITICAL
     --#TIMEINDEX 100
     --#STATE OPERATIONAL
::= 9663


hpevtFabricAssertFabricHop TRAP-TYPE
     ENTERPRISE hpIpfE0Events
     VARIABLES { hpIpfEvtDetailStr }
     DESCRIPTION
        "An unexpected error occurred while initializing the fabric.  The firmware is not able to analyze this error.  Clues to the cause of this error may be found in the IPMI forward progress log (FPL) either shortly before or after this log entry occurred.  The FPL is available from the management processor using the 'sl' command.  HP-UX also saves these logs in the /var/stm/logs/os directory, and they can be viewed using the slview utility."

     --#SUMMARY "Unexpected fabric firmware error"
     --#ARGUMENTS {}
     --#SEVERITY WARNING
     --#TIMEINDEX 100
     --#STATE OPERATIONAL
::= 9666


hpevtBootFailedReadingProfileCInIcm TRAP-TYPE
     ENTERPRISE hpIpfE0Events
     VARIABLES { hpIpfEvtDetailStr }
     DESCRIPTION
        "PDC could not access a complex profile. The partition will be reset. 
 
Data field contains the return status from the function that encountered the error."

     --#SUMMARY "PDC could not read the copy of profile C stored in ICM"
     --#ARGUMENTS {}
     --#SEVERITY CRITICAL
     --#TIMEINDEX 100
     --#STATE OPERATIONAL
::= 9668


hpevtFabricHaltLinkDisableErr TRAP-TYPE
     ENTERPRISE hpIpfE0Events
     VARIABLES { hpIpfEvtDetailStr }
     DESCRIPTION
        "Before attempting a fabricless boot, the cell's link to the fabric should be disabled to provide isolation and stability.  The link could not be disabled, so the cell will halt."

     --#SUMMARY "Could not disable the XIN link before a fabricless boot"
     --#ARGUMENTS {}
     --#SEVERITY CRITICAL
     --#TIMEINDEX 100
     --#STATE OPERATIONAL
::= 9670


hpevtBootGetSpiromGetSiblingErr TRAP-TYPE
     ENTERPRISE hpIpfE0Events
     VARIABLES { hpIpfEvtDetailStr }
     DESCRIPTION
        "Configuration information on the processor was invalid.  The cell will be halted. 
 
Data field contains the return value from the function that encountered the error."

     --#SUMMARY "Fail to GetSiblingCpuCoreNum() in BootGetSpiromData()"
     --#ARGUMENTS {}
     --#SEVERITY WARNING
     --#TIMEINDEX 100
     --#STATE OPERATIONAL
::= 9674


hpevtCpuClockRatioMismatch TRAP-TYPE
     ENTERPRISE hpIpfE0Events
     VARIABLES { hpIpfEvtDetailStr }
     DESCRIPTION
        "The clock ratio that the processor is running at does not match the clock ratio that manageability is reporting."

     --#SUMMARY "The clock ratio reported by manageability does not match the actual clock ratio"
     --#ARGUMENTS {}
     --#SEVERITY CRITICAL
     --#TIMEINDEX 100
     --#STATE OPERATIONAL
::= 9678


hpevtBootStopBootOverride TRAP-TYPE
     ENTERPRISE hpIpfE0Events
     VARIABLES { hpIpfEvtDetailStr }
     DESCRIPTION
        "The user has manually bypassed a stop boot condition (caused by an error during boot) and continued to boot an O/S.  The system might experience unpredictable failures."

     --#SUMMARY "Manual override of fatal stop boot condition"
     --#ARGUMENTS {}
     --#SEVERITY CRITICAL
     --#TIMEINDEX 100
     --#STATE OPERATIONAL
::= 9681


hpevtVgaBiosRelocFail TRAP-TYPE
     ENTERPRISE hpIpfE0Events
     VARIABLES { hpIpfEvtDetailStr }
     DESCRIPTION
        "Firmware was unable to relocate the VGA BIOS to the hardcoded VGA BIOS region in main memory (physical address range 0xc0000 - 0xdffff).  VGA routing has been disabled by firmware.  No VGA device will be accessible on this boot."

     --#SUMMARY "Firmware unable to relocate VGA BIOS"
     --#ARGUMENTS {}
     --#SEVERITY WARNING
     --#TIMEINDEX 100
     --#STATE OPERATIONAL
::= 9682


hpevtCompMatrixXsumError TRAP-TYPE
     ENTERPRISE hpIpfE0Events
     VARIABLES { hpIpfEvtDetailStr }
     DESCRIPTION
        "The componenet compatability matrix stored in NVRAM and used by system firmware has a checksum error.  The stored value does not equal the calculated value.  The data field will contain first the expected value, and the subsequent code will contain the actual data."

     --#SUMMARY "The Compatability Matrix stored in NVRAM has a checksum error"
     --#ARGUMENTS {}
     --#SEVERITY CRITICAL
     --#TIMEINDEX 100
     --#STATE OPERATIONAL
::= 9685


hpevtBootGetDefaultRdrsFailed TRAP-TYPE
     ENTERPRISE hpIpfE0Events
     VARIABLES { hpIpfEvtDetailStr }
     DESCRIPTION
        "PDC could not read an internal CPU register.  The partition will be reset. 
 
Data field is the return status from the function that encountered the error."

     --#SUMMARY "PDC failed its attempt to get default RDR values"
     --#ARGUMENTS {}
     --#SEVERITY CRITICAL
     --#TIMEINDEX 100
     --#STATE OPERATIONAL
::= 9695


hpevtBootGetCurrentRdrsFailed TRAP-TYPE
     ENTERPRISE hpIpfE0Events
     VARIABLES { hpIpfEvtDetailStr }
     DESCRIPTION
        "PDC could not read an internal CPU register.  The partition will be reset. 
 
Data field is the return status from the function that encountered the error."

     --#SUMMARY "PDC could not read current RDR values of the executing CPU"
     --#ARGUMENTS {}
     --#SEVERITY CRITICAL
     --#TIMEINDEX 100
     --#STATE OPERATIONAL
::= 9696


hpevtBootReadPrefetchFailed TRAP-TYPE
     ENTERPRISE hpIpfE0Events
     VARIABLES { hpIpfEvtDetailStr }
     DESCRIPTION
        "PDC failed reading a value out of its own copy of the internal CPU register settings.  Data field is a status return indicating the type of failure."

     --#SUMMARY "PDC failed reading a specific value from its own copy of the RDRs"
     --#ARGUMENTS {}
     --#SEVERITY CRITICAL
     --#TIMEINDEX 100
     --#STATE OPERATIONAL
::= 9697


hpevtBootReadZlcoFailed TRAP-TYPE
     ENTERPRISE hpIpfE0Events
     VARIABLES { hpIpfEvtDetailStr }
     DESCRIPTION
        "PDC failed reading a value out of its own copy of the internal CPU register settings.  Data field is a status return indicating the type of failure."

     --#SUMMARY "PDC failed reading a specific value from its own copy of the RDRs"
     --#ARGUMENTS {}
     --#SEVERITY CRITICAL
     --#TIMEINDEX 100
     --#STATE OPERATIONAL
::= 9698


hpevtBootUpdateZlcoAndPrefetchFailed TRAP-TYPE
     ENTERPRISE hpIpfE0Events
     VARIABLES { hpIpfEvtDetailStr }
     DESCRIPTION
        "PDC attempted to update CPU registers to match their respective settings in the complex profile, but a failure was returned from the call to accomplish the update.  Data field contains the failure."

     --#SUMMARY "PDC failed attempting to update ZLCO and PREFETCH RDR settings"
     --#ARGUMENTS {}
     --#SEVERITY CRITICAL
     --#TIMEINDEX 100
     --#STATE OPERATIONAL
::= 9700


hpevtBootErrorReadingZlcoFlagInPdProfile TRAP-TYPE
     ENTERPRISE hpIpfE0Events
     VARIABLES { hpIpfEvtDetailStr }
     DESCRIPTION
        "PDC could not access a complex profile. The partition will be reset.. 
 
Data field contains the return status from the function that encountered the error."

     --#SUMMARY "PDC failed to read the HV Flag in the Partition Configuration Data"
     --#ARGUMENTS {}
     --#SEVERITY CRITICAL
     --#TIMEINDEX 100
     --#STATE OPERATIONAL
::= 9701


hpevtBootFindCoreCellCmplxProfileAcErr TRAP-TYPE
     ENTERPRISE hpIpfE0Events
     VARIABLES { hpIpfEvtDetailStr }
     DESCRIPTION
        "PDC could not access a complex profile. The cell will be reset. 
 
Data field contains the return status from the function that encountered the error."

     --#SUMMARY "Failed to get the configured set from the Complex Profiles A and C"
     --#ARGUMENTS {}
     --#SEVERITY WARNING
     --#TIMEINDEX 100
     --#STATE OPERATIONAL
::= 9706


hpevtBootFindCoreCellConfigSelectErr TRAP-TYPE
     ENTERPRISE hpIpfE0Events
     VARIABLES { hpIpfEvtDetailStr }
     DESCRIPTION
        "Could not find a potential core cell for the partition in the configured set.  This cell will reset for reconfiguration.  Data Field: return status from failing function"

     --#SUMMARY "No possible core cells were found in the configured set"
     --#ARGUMENTS {}
     --#SEVERITY WARNING
     --#TIMEINDEX 100
     --#STATE OPERATIONAL
::= 9707


hpevtBootCellLclCantFindViable TRAP-TYPE
     ENTERPRISE hpIpfE0Events
     VARIABLES { hpIpfEvtDetailStr }
     DESCRIPTION
        "The potential core cell was not viable (ie. no core I/O, etc).  This cell will reset for reconfiguration.  Data Field: bit mask of cells that made the rendezvous set"

     --#SUMMARY "Could not find a viable core cell in the partition"
     --#ARGUMENTS {}
     --#SEVERITY WARNING
     --#TIMEINDEX 100
     --#STATE OPERATIONAL
::= 9708


hpevtBootCellRmtCantFindViable TRAP-TYPE
     ENTERPRISE hpIpfE0Events
     VARIABLES { hpIpfEvtDetailStr }
     DESCRIPTION
        "The potential core cell was not viable (ie. no core I/O, etc).  This cell will reset for reconfiguration.   
 
Data Field: bit mask of cells that made the rendezvous set"

     --#SUMMARY "Could not find a viable core cell in the partition"
     --#ARGUMENTS {}
     --#SEVERITY WARNING
     --#TIMEINDEX 100
     --#STATE OPERATIONAL
::= 9709


hpevtBootFindCoreCellNotInRendez TRAP-TYPE
     ENTERPRISE hpIpfE0Events
     VARIABLES { hpIpfEvtDetailStr }
     DESCRIPTION
        "The potential core cell did not rendezvous with the rest of the partition.  This cell cannot talk to the selected core cell.  This cell will reset for reconfiguration.  Data Field: bit mask of cells that made the rendezvous set"

     --#SUMMARY "The core cell selected is not in the rendezvoused partition"
     --#ARGUMENTS {}
     --#SEVERITY WARNING
     --#TIMEINDEX 100
     --#STATE OPERATIONAL
::= 9710


hpevtBootFindCoreCellLclNotViable TRAP-TYPE
     ENTERPRISE hpIpfE0Events
     VARIABLES { hpIpfEvtDetailStr }
     DESCRIPTION
        "The local cell is disconnected from the rest of the system due to the main backplane configuration.  While the partition is only configured to contain a single cell, the local cell is not a viable core cell.  The cell will reset for reconfiguration.  Data Field: bit mask of cells that made the rendezvous set"

     --#SUMMARY "The local cell is not viable"
     --#ARGUMENTS {}
     --#SEVERITY WARNING
     --#TIMEINDEX 100
     --#STATE OPERATIONAL
::= 9711


hpevtBootFindCoreCellFabriclessPdErr TRAP-TYPE
     ENTERPRISE hpIpfE0Events
     VARIABLES { hpIpfEvtDetailStr }
     DESCRIPTION
        "This cell has booted without the main backplane, probably due to prior main backplane errors.  The partition it is in is configured with 3 or more cells.  The combination of these two configurations is not allowed.  The cell will reset for reconfiguration.  Data Field: configured set"

     --#SUMMARY "cell cannot reach the fabric, partition contains 3 or more cells"
     --#ARGUMENTS {}
     --#SEVERITY WARNING
     --#TIMEINDEX 100
     --#STATE OPERATIONAL
::= 9712


hpevtRtcAccessError TRAP-TYPE
     ENTERPRISE hpIpfE0Events
     VARIABLES { hpIpfEvtDetailStr }
     DESCRIPTION
        "While validating the internal RTC data the data is read twice and compared.  If the comparison fails to match the read is performed again up a maximum of 50 times.  If we cannot get a match in 50 retries we issue this event."

     --#SUMMARY "The RTC is providing inconsistent data."
     --#ARGUMENTS {}
     --#SEVERITY WARNING
     --#TIMEINDEX 100
     --#STATE OPERATIONAL
::= 9719


hpevtBootAccessCellArchErr TRAP-TYPE
     ENTERPRISE hpIpfE0Events
     VARIABLES { hpIpfEvtDetailStr }
     DESCRIPTION
        "PDC attempts to make sure that all of the cells in a partition are installed in the same processor architecture. PDC failed to read the architecture for another cell.  PDC will reset all of the cells in the partition when this error is detected. 
 
The data field contains the physical location of the cell reporting the event."

     --#SUMMARY "PDC failed to read the processor architecture for another cell in the partition"
     --#ARGUMENTS {}
     --#SEVERITY CRITICAL
     --#TIMEINDEX 100
     --#STATE OPERATIONAL
::= 9727


hpevtXbcLogSizeErr TRAP-TYPE
     ENTERPRISE hpIpfE0Events
     VARIABLES { hpIpfEvtDetailStr }
     DESCRIPTION
        "The buffer size passed in to the XBC error logging routine through SAL_GET_STATE_INFO, SAL_CLEAR_STATE_INFO, or MCA logging is too small for the XBC error log 
Data field consists of: XBC number (32:43)"

     --#SUMMARY "The buffer size is too small for the XBC error log"
     --#ARGUMENTS {}
     --#SEVERITY CRITICAL
     --#TIMEINDEX 100
     --#STATE OPERATIONAL
::= 9740


hpevtXbcLogClearErr TRAP-TYPE
     ENTERPRISE hpIpfE0Events
     VARIABLES { hpIpfEvtDetailStr }
     DESCRIPTION
        "System firmware was unable to clear an XBC error.   
The data field contains:  XBC number (32:43) 
                                       port number (44:55) 
                                       error type (0:31)"

     --#SUMMARY "System firmware was unable to clear an XBC error"
     --#ARGUMENTS {}
     --#SEVERITY CRITICAL
     --#TIMEINDEX 100
     --#STATE OPERATIONAL
::= 9741


hpevtCabPowerTimeout TRAP-TYPE
     ENTERPRISE hpIpfE0Events
     VARIABLES { hpIpfEvtDetailStr }
     DESCRIPTION
        "System Firmware detected a possible timeout waiting for the other cabinet to power on.  System firmware queried the utilities system to see what cells are installed.  This indicated that cells are installed in the other cabinet but none are powered on.  Firmware delayed fabric routing, waiting for the other cabinet cells to power on, but eventually timed out and went on."

     --#SUMMARY "Firmware detected a possible Cabinet Power Timeout"
     --#ARGUMENTS {}
     --#SEVERITY WARNING
     --#TIMEINDEX 100
     --#STATE OPERATIONAL
::= 9742


hpevtIodiscPciLogError TRAP-TYPE
     ENTERPRISE hpIpfE0Events
     VARIABLES { hpIpfEvtDetailStr }
     DESCRIPTION
        "Error encountered while collecting PCI error logs"

     --#SUMMARY "Error encountered while collecting PCI error logs"
     --#ARGUMENTS {}
     --#SEVERITY CRITICAL
     --#TIMEINDEX 100
     --#STATE OPERATIONAL
::= 9744


hpevtIodiscSbaLogError TRAP-TYPE
     ENTERPRISE hpIpfE0Events
     VARIABLES { hpIpfEvtDetailStr }
     DESCRIPTION
        "Error encountered while collecting SBA error logs"

     --#SUMMARY "Error encountered while collecting SBA error logs"
     --#ARGUMENTS {}
     --#SEVERITY CRITICAL
     --#TIMEINDEX 100
     --#STATE OPERATIONAL
::= 9745


hpevtXbcInitMaxRetries TRAP-TYPE
     ENTERPRISE hpIpfE0Events
     VARIABLES { hpIpfEvtDetailStr }
     DESCRIPTION
        "During fabric initialization, if a crossbar is found to be in an unexpected state, the number of retries is incremented.  If the number of retries exceeds the maximum, then something is wrong and there is no way to initialize the fabric. 
Data field: number of retries (0:31), crossbar number (32:63)"

     --#SUMMARY "Fabric is unable to route the crossbar after multiple retry attempts"
     --#ARGUMENTS {}
     --#SEVERITY CRITICAL
     --#TIMEINDEX 100
     --#STATE OPERATIONAL
::= 9746


hpevtWinAgtPredictMemFailWarning TRAP-TYPE
     ENTERPRISE hpIpfE0Events
     VARIABLES { hpIpfEvtDetailStr }
     DESCRIPTION
        "ECC (Error Checking and Correcting) memory is designed to detect and correct single-bit errors that occasionally occur in computer systems.  This memory module is currently correcting many single bit errors."

     --#SUMMARY "Windows: Predictive Failure in Memory (Warning)"
     --#ARGUMENTS {}
     --#SEVERITY WARNING
     --#TIMEINDEX 100
     --#STATE OPERATIONAL
::= 9750


hpevtWinAgtPredictMemFailCritical TRAP-TYPE
     ENTERPRISE hpIpfE0Events
     VARIABLES { hpIpfEvtDetailStr }
     DESCRIPTION
        "ECC (Error Checking and Correcting) memory is designed to detect and correct single-bit errors that occasionally occur in computer systems.  This memory module is currently correcting many single bit errors."

     --#SUMMARY "Windows: Predictive Failure in Memory (Critical)"
     --#ARGUMENTS {}
     --#SEVERITY CRITICAL
     --#TIMEINDEX 100
     --#STATE OPERATIONAL
::= 9751


hpevtPciFatalRopeParityErr TRAP-TYPE
     ENTERPRISE hpIpfE0Events
     VARIABLES { hpIpfEvtDetailStr }
     DESCRIPTION
        "A error occurred on the bus connecting the PCI card to the system bus."

     --#SUMMARY "A rope parity error occurred"
     --#ARGUMENTS {}
     --#SEVERITY CRITICAL
     --#TIMEINDEX 100
     --#STATE OPERATIONAL
::= 9753


hpevtPciFatalBusError TRAP-TYPE
     ENTERPRISE hpIpfE0Events
     VARIABLES { hpIpfEvtDetailStr }
     DESCRIPTION
        "A PCI card has been marked as 'fatal' by the operating system due to a bus error.  The LBA has been isolated by the operating system due to an error which occured in a device(s) connected to that LBA."

     --#SUMMARY "PCI card inaccessible due to bus error"
     --#ARGUMENTS {}
     --#SEVERITY CRITICAL
     --#TIMEINDEX 100
     --#STATE OPERATIONAL
::= 9754


hpevtPciFatalDeviceError TRAP-TYPE
     ENTERPRISE hpIpfE0Events
     VARIABLES { hpIpfEvtDetailStr }
     DESCRIPTION
        "A PCI card has been marked as 'fatal' by the operating system due to a device error."

     --#SUMMARY "PCI card inaccessible due to device error"
     --#ARGUMENTS {}
     --#SEVERITY CRITICAL
     --#TIMEINDEX 100
     --#STATE OPERATIONAL
::= 9755


hpevtBootErrorReadingFirstBootToken TRAP-TYPE
     ENTERPRISE hpIpfE0Events
     VARIABLES { hpIpfEvtDetailStr }
     DESCRIPTION
        "Firmware tried to read the first boot token an got a failure.  The data field contains the token number that FW tried to read.  This is a stop boot condition"

     --#SUMMARY "error reading bmc first boot token"
     --#ARGUMENTS {}
     --#SEVERITY CRITICAL
     --#TIMEINDEX 100
     --#STATE OPERATIONAL
::= 9768


hpevtBootNonPaCellDetected TRAP-TYPE
     ENTERPRISE hpIpfE0Events
     VARIABLES { hpIpfEvtDetailStr }
     DESCRIPTION
        "monarch PA cell has detected that a cell it is attempting to rendezvous into its PD is not a PA cell and is thus incompatible."

     --#SUMMARY "a rendezvousing cell is non PA architecture and thus incompatible."
     --#ARGUMENTS {}
     --#SEVERITY WARNING
     --#TIMEINDEX 100
     --#STATE OPERATIONAL
::= 9769


hpevtFabricErrorsXbcClearWrErr TRAP-TYPE
     ENTERPRISE hpIpfE0Events
     VARIABLES { hpIpfEvtDetailStr }
     DESCRIPTION
        "A XBC error could not be cleared due to a write failure.  The data field indicates the type of error: (XBC Port Num << 56) | (XBC Num << 32) | error status"

     --#SUMMARY "failed to write the XBC error log clear register"
     --#ARGUMENTS {}
     --#SEVERITY WARNING
     --#TIMEINDEX 100
     --#STATE OPERATIONAL
::= 9774


hpevtFabricErrorsXbcClearRdGlblErr TRAP-TYPE
     ENTERPRISE hpIpfE0Events
     VARIABLES { hpIpfEvtDetailStr }
     DESCRIPTION
        "Failed to read the XBC Global CSR Error Status register.  Data Field: (XBC Port Num << 56) | (XBC Num << 32) | error status"

     --#SUMMARY "Error encounted while reading the XBC CSR Error Status Register"
     --#ARGUMENTS {}
     --#SEVERITY WARNING
     --#TIMEINDEX 100
     --#STATE OPERATIONAL
::= 9775


hpevtFabricErrorsXbcClrLoSevErr TRAP-TYPE
     ENTERPRISE hpIpfE0Events
     VARIABLES { hpIpfEvtDetailStr }
     DESCRIPTION
        "The XBC CSR Low Severity error was not cleared or more errors remain.  Data Field: (XBC Port Num << 56) | (XBC Num << 32) | contents of the XBC CSR Error Status Register"

     --#SUMMARY "The XBC CSR Low Severity error was not cleared"
     --#ARGUMENTS {}
     --#SEVERITY WARNING
     --#TIMEINDEX 100
     --#STATE OPERATIONAL
::= 9776


hpevtFabricErrorsXbcClrHiSevErr TRAP-TYPE
     ENTERPRISE hpIpfE0Events
     VARIABLES { hpIpfEvtDetailStr }
     DESCRIPTION
        "The XBC CSR High Severity error was not cleared or more errors remain.  Data Field: (XBC Port Num << 56) | (XBC Num << 32) | contents of the XBC CSR Error Status Register"

     --#SUMMARY "The XBC CSR High Severity error was not cleared"
     --#ARGUMENTS {}
     --#SEVERITY WARNING
     --#TIMEINDEX 100
     --#STATE OPERATIONAL
::= 9777


hpevtFabricErrorsXbcClearRdPortErr TRAP-TYPE
     ENTERPRISE hpIpfE0Events
     VARIABLES { hpIpfEvtDetailStr }
     DESCRIPTION
        "Failed to read the XBC Port Error Status register.  Data Field: (XBC Port Num << 56) | (XBC Num << 32) | error status"

     --#SUMMARY "Error encounted while reading the XBC Port Error Status Register"
     --#ARGUMENTS {}
     --#SEVERITY WARNING
     --#TIMEINDEX 100
     --#STATE OPERATIONAL
::= 9778


hpevtFabricErrsCsrLogClrRdSlicesErr TRAP-TYPE
     ENTERPRISE hpIpfE0Events
     VARIABLES { hpIpfEvtDetailStr }
     DESCRIPTION
        "Failed to read the XBC Global CSR Error Status register.  Data Field: (XBC Port Num << 56) | error status"

     --#SUMMARY "Failed to read the XBC CSR Error Status register"
     --#ARGUMENTS {}
     --#SEVERITY WARNING
     --#TIMEINDEX 100
     --#STATE OPERATIONAL
::= 9780


hpevtFabricErrsCsrLogClrCopyBlk0Err TRAP-TYPE
     ENTERPRISE hpIpfE0Events
     VARIABLES { hpIpfEvtDetailStr }
     DESCRIPTION
        "Firmware failed to copy the XBC CSR Error symbol 01 registers into a data structure on the stack.  Data Field: address where the register contents are being copied"

     --#SUMMARY "Failed to copy the XBC CSR Error Symbol01 Block"
     --#ARGUMENTS {}
     --#SEVERITY WARNING
     --#TIMEINDEX 100
     --#STATE OPERATIONAL
::= 9781


hpevtFabricErrsCsrLogClrCopyBlk2Err TRAP-TYPE
     ENTERPRISE hpIpfE0Events
     VARIABLES { hpIpfEvtDetailStr }
     DESCRIPTION
        "Firmware failed to copy the XBC CSR Error symbol 23 registers into a data structure on the stack.  Data Field: address where the register contents are being copied"

     --#SUMMARY "Failed to copy the XBC CSR Error Symbol23 Block"
     --#ARGUMENTS {}
     --#SEVERITY WARNING
     --#TIMEINDEX 100
     --#STATE OPERATIONAL
::= 9782


hpevtFabricXbcLoStateResetErr TRAP-TYPE
     ENTERPRISE hpIpfE0Events
     VARIABLES { hpIpfEvtDetailStr }
     DESCRIPTION
        "Firmware was unable to reset the XBC CSR Low Severity error log state.  Data Field: (XBC Port Num << 56) | (XBC Num << 32) | error status"

     --#SUMMARY "Failed to reset the XBC Low Severity Error Log State"
     --#ARGUMENTS {}
     --#SEVERITY WARNING
     --#TIMEINDEX 100
     --#STATE OPERATIONAL
::= 9783


hpevtFabricClrXbcSym01Failure TRAP-TYPE
     ENTERPRISE hpIpfE0Events
     VARIABLES { hpIpfEvtDetailStr }
     DESCRIPTION
        "The XBC Low Severity error logs were not cleared.  Data Field: (XBC Port Num << 56) | (XBC Num << 32) | number of failed clear attempts"

     --#SUMMARY "Failed to clear the XBC Low Severity Log Symbol 01"
     --#ARGUMENTS {}
     --#SEVERITY WARNING
     --#TIMEINDEX 100
     --#STATE OPERATIONAL
::= 9784


hpevtFabricClrXbcIsLoCsrErrErr TRAP-TYPE
     ENTERPRISE hpIpfE0Events
     VARIABLES { hpIpfEvtDetailStr }
     DESCRIPTION
        "Reading the XBC CSR Error Status register failed.  Data field: (XBC Port Num << 56) | (XBC Num << 32) | error status"

     --#SUMMARY "Could not determine if there is a new XBC CSR Low Severity error"
     --#ARGUMENTS {}
     --#SEVERITY WARNING
     --#TIMEINDEX 100
     --#STATE OPERATIONAL
::= 9785


hpevtFabricClrXbcRdLoLogStateErr TRAP-TYPE
     ENTERPRISE hpIpfE0Events
     VARIABLES { hpIpfEvtDetailStr }
     DESCRIPTION
        "Failed to read a XBC Global scratch register that indicates if new, unlogged errors have been encountered. Data field: (XBC Port Num << 56) | (XBC Num << 32) | error status"

     --#SUMMARY "Failed to read the XBC CSR Low Severity Error Log State"
     --#ARGUMENTS {}
     --#SEVERITY WARNING
     --#TIMEINDEX 100
     --#STATE OPERATIONAL
::= 9786


hpevtFabricXbcHiStateResetErr TRAP-TYPE
     ENTERPRISE hpIpfE0Events
     VARIABLES { hpIpfEvtDetailStr }
     DESCRIPTION
        "Firmware was unable to reset the XBC CSR Low Severity error log state.  Data Field: (XBC Port Num << 56) | (XBC Num << 32) | error status"

     --#SUMMARY "Failed to reset the XBC Low Severity Error Log State"
     --#ARGUMENTS {}
     --#SEVERITY WARNING
     --#TIMEINDEX 100
     --#STATE OPERATIONAL
::= 9787


hpevtFabricClrXbcIsHiCsrErrErr TRAP-TYPE
     ENTERPRISE hpIpfE0Events
     VARIABLES { hpIpfEvtDetailStr }
     DESCRIPTION
        "Reading the XBC CSR Error Status register failed.  Data field: (XBC Port Num << 56) | (XBC Num << 32) | error status"

     --#SUMMARY "Could not determine if there is a new XBC CSR High Severity error"
     --#ARGUMENTS {}
     --#SEVERITY WARNING
     --#TIMEINDEX 100
     --#STATE OPERATIONAL
::= 9788


hpevtFabricClrXbcRdHiLogStateErr TRAP-TYPE
     ENTERPRISE hpIpfE0Events
     VARIABLES { hpIpfEvtDetailStr }
     DESCRIPTION
        "Failed to read a XBC Global scratch register that indicates if new, unlogged errors have been encountered. Data field: (XBC Port Num << 56) | (XBC Num << 32) | error status"

     --#SUMMARY "Failed to read the XBC CSR High Severity Error Log State"
     --#ARGUMENTS {}
     --#SEVERITY WARNING
     --#TIMEINDEX 100
     --#STATE OPERATIONAL
::= 9789


hpevtPlatformCacheHashingError TRAP-TYPE
     ENTERPRISE hpIpfE0Events
     VARIABLES { hpIpfEvtDetailStr }
     DESCRIPTION
        "An error occurred while enabling hashing in the platform cache.  The data field contains the status."

     --#SUMMARY "An error occurred while enabling hashing in the platform cache"
     --#ARGUMENTS {}
     --#SEVERITY CRITICAL
     --#TIMEINDEX 100
     --#STATE OPERATIONAL
::= 9801


hpevtFabricXbcWriteableInvalidCsr TRAP-TYPE
     ENTERPRISE hpIpfE0Events
     VARIABLES { hpIpfEvtDetailStr }
     DESCRIPTION
        "A write to an invalid XBC CSR address was attempted.  The write will not be allowed.  The severity of this result will be determined by the calling function.  Data Field: XBC CSR address that was attempted"

     --#SUMMARY "The XBC CSR is not a valid CSR address"
     --#ARGUMENTS {}
     --#SEVERITY WARNING
     --#TIMEINDEX 100
     --#STATE OPERATIONAL
::= 9827


hpevtMcCellsLostConnection TRAP-TYPE
     ENTERPRISE hpIpfE0Events
     VARIABLES { hpIpfEvtDetailStr }
     DESCRIPTION
        "It indicates loss of cell connectivity in the partition during a global MCA processing."

     --#SUMMARY "It indicates loss of cell connectivity in the partition."
     --#ARGUMENTS {}
     --#SEVERITY CRITICAL
     --#TIMEINDEX 100
     --#STATE OPERATIONAL
::= 9832


hpevtBuildErrCellDevTree TRAP-TYPE
     ENTERPRISE hpIpfE0Events
     VARIABLES { hpIpfEvtDetailStr }
     DESCRIPTION
        "Error status of building the cell-level firmware device tree"

     --#SUMMARY "Error building cell-level FW device tree"
     --#ARGUMENTS {}
     --#SEVERITY CRITICAL
     --#TIMEINDEX 100
     --#STATE OPERATIONAL
::= 9849


hpevtDcnfgFsbInit TRAP-TYPE
     ENTERPRISE hpIpfE0Events
     VARIABLES { hpIpfEvtDetailStr }
     DESCRIPTION
        "An error has occurred during CPU FSB interface initialization.  The datafield contains a 32-bit error number and 32-bits of additional error information.  The CPU will be deconfigured."

     --#SUMMARY "CPU deconfigured during FSB interface initialization"
     --#ARGUMENTS {}
     --#SEVERITY WARNING
     --#TIMEINDEX 100
     --#STATE OPERATIONAL
::= 9867


hpevtDcnfgCpuParams TRAP-TYPE
     ENTERPRISE hpIpfE0Events
     VARIABLES { hpIpfEvtDetailStr }
     DESCRIPTION
        "An error has occurred while obtaining CPU parameters from the CPU abstraction layer.  The datafield contains a 32-bit error number and 32-bits of additional error information.  The CPU will be deconfigured."

     --#SUMMARY "CPU deconfigured due to error obtaining parameters from PAL"
     --#ARGUMENTS {}
     --#SEVERITY WARNING
     --#TIMEINDEX 100
     --#STATE OPERATIONAL
::= 9868


hpevtDcnfgCpuIcache TRAP-TYPE
     ENTERPRISE hpIpfE0Events
     VARIABLES { hpIpfEvtDetailStr }
     DESCRIPTION
        "An error occurred while getting CPU icache parameters from the CPU abstraction layer.  The datafield contains a 32-bit error number and 32-bits of additional error information.  The CPU will be deconfigured if this error occurs during system boot."

     --#SUMMARY "CPU deconfigured due to failure retrieving icache parameters from PAL"
     --#ARGUMENTS {}
     --#SEVERITY WARNING
     --#TIMEINDEX 100
     --#STATE OPERATIONAL
::= 9869


hpevtDcnfgCpuDcache TRAP-TYPE
     ENTERPRISE hpIpfE0Events
     VARIABLES { hpIpfEvtDetailStr }
     DESCRIPTION
        "An error occurred while obtaining CPU dcache parameters from the CPU abstraction layer.  The datafield contains a 32-bit error number and 32-bits of additional error information.  The CPU will be deconfigured if error occurs during system boot."

     --#SUMMARY "CPU deconfigured during initialization process"
     --#ARGUMENTS {}
     --#SEVERITY WARNING
     --#TIMEINDEX 100
     --#STATE OPERATIONAL
::= 9870


hpevtDcnfgCpuCacheState TRAP-TYPE
     ENTERPRISE hpIpfE0Events
     VARIABLES { hpIpfEvtDetailStr }
     DESCRIPTION
        "An error occurred while initializing the CPU cache to a known state.  The datafield contains a 32-bit error number and 32-bits of additional error information.  The CPU will be deconfigured."

     --#SUMMARY "CPU deconfigured during dcache init"
     --#ARGUMENTS {}
     --#SEVERITY WARNING
     --#TIMEINDEX 100
     --#STATE OPERATIONAL
::= 9871


hpevtDcnfgCpuCacheMonitor TRAP-TYPE
     ENTERPRISE hpIpfE0Events
     VARIABLES { hpIpfEvtDetailStr }
     DESCRIPTION
        "An error occurred while enabling CPU cache error monitoring.  The datafield contains a 32-bit error number and 32-bits of additional error information.  The CPU will be deconfigured."

     --#SUMMARY "CPU deconfigured due to internal error"
     --#ARGUMENTS {}
     --#SEVERITY WARNING
     --#TIMEINDEX 100
     --#STATE OPERATIONAL
::= 9872


hpevtDcnfgCpuMca TRAP-TYPE
     ENTERPRISE hpIpfE0Events
     VARIABLES { hpIpfEvtDetailStr }
     DESCRIPTION
        "An error occurred while enabling some machine error check traps on a CPU.  The datafield contains a 32-bit error number and 32-bits of additional error information.  The CPU will be deconfigured."

     --#SUMMARY "CPU deconfigured due to machine check"
     --#ARGUMENTS {}
     --#SEVERITY WARNING
     --#TIMEINDEX 100
     --#STATE OPERATIONAL
::= 9873


hpevtDcnfgCpuDisableMca TRAP-TYPE
     ENTERPRISE hpIpfE0Events
     VARIABLES { hpIpfEvtDetailStr }
     DESCRIPTION
        "An error occurred while disabling maching error check traps on a CPU.  The datafield contains a 32-bit error number and 32-bits of additional error information.  The CPU will be deconfigured."

     --#SUMMARY "CPU deconfigured due to error while disabling machine check"
     --#ARGUMENTS {}
     --#SEVERITY WARNING
     --#TIMEINDEX 100
     --#STATE OPERATIONAL
::= 9874


hpevtDcnfgCpuSelfTest TRAP-TYPE
     ENTERPRISE hpIpfE0Events
     VARIABLES { hpIpfEvtDetailStr }
     DESCRIPTION
        "An error occurred during the serialized CPU late selftests.  The datafield contains a 32-bit error number and 32-bits of additional error information.  The CPU will be deconfigured."

     --#SUMMARY "CPU deconfigured due to failure in late self tests"
     --#ARGUMENTS {}
     --#SEVERITY WARNING
     --#TIMEINDEX 100
     --#STATE OPERATIONAL
::= 9875


hpevtDcnfgCpuL2Cache TRAP-TYPE
     ENTERPRISE hpIpfE0Events
     VARIABLES { hpIpfEvtDetailStr }
     DESCRIPTION
        "An error occurred while enabling the CPU L2 shared cache.  The datafield contains a 32-bit error number and 32-bits of additional error information.  The CPU will be deconfigured."

     --#SUMMARY "CPU deconfigured while enabling L2 shared cache"
     --#ARGUMENTS {}
     --#SEVERITY WARNING
     --#TIMEINDEX 100
     --#STATE OPERATIONAL
::= 9876


hpevtDcnfgCpuDefValue TRAP-TYPE
     ENTERPRISE hpIpfE0Events
     VARIABLES { hpIpfEvtDetailStr }
     DESCRIPTION
        "An error while getting default values for programmable CPU internal registers from the CPU abstraction layer.  The datafield contains a 32-bit error number and 32-bits of additional error information.  The CPU will be deconfigured."

     --#SUMMARY "CPU deconfigured while retrieving default values from PAL"
     --#ARGUMENTS {}
     --#SEVERITY WARNING
     --#TIMEINDEX 100
     --#STATE OPERATIONAL
::= 9877


hpevtDcnfgCpuInReg TRAP-TYPE
     ENTERPRISE hpIpfE0Events
     VARIABLES { hpIpfEvtDetailStr }
     DESCRIPTION
        "An error occurred while getting an address for a CPU internal register within a buffer from the CPU abstraction layer.  The datafield contains a 32-bit error number and 32-bits of additional error information.  The CPU will be deconfigured."

     --#SUMMARY "CPU deconfigured getting an address for a CPU internal register within a buffer from the CPU abstraction layer"
     --#ARGUMENTS {}
     --#SEVERITY WARNING
     --#TIMEINDEX 100
     --#STATE OPERATIONAL
::= 9878


hpevtDcnfgCpuProgReg TRAP-TYPE
     ENTERPRISE hpIpfE0Events
     VARIABLES { hpIpfEvtDetailStr }
     DESCRIPTION
        "An error occurred while programming CPU internal registers with final configuration values.  The datafield contains a 32-bit error number and 32-bits of additional error information.  The CPU will be deconfigured."

     --#SUMMARY "CPU deconfigured while getting an address for a CPU internal register within a buffer from the CPU abstraction layer"
     --#ARGUMENTS {}
     --#SEVERITY WARNING
     --#TIMEINDEX 100
     --#STATE OPERATIONAL
::= 9879


hpevtNoMemSelfTest TRAP-TYPE
     ENTERPRISE hpIpfE0Events
     VARIABLES { hpIpfEvtDetailStr }
     DESCRIPTION
        "There was not enough error free memory in the system to run the late selftests."

     --#SUMMARY "Not enough error free memory to run late sefltests"
     --#ARGUMENTS {}
     --#SEVERITY CRITICAL
     --#TIMEINDEX 100
     --#STATE OPERATIONAL
::= 9896


hpevtCellLatchOpen TRAP-TYPE
     ENTERPRISE hpIpfE0Events
     VARIABLES { hpIpfEvtDetailStr }
     DESCRIPTION
        "The left cell ejector on the specified cell is open."

     --#SUMMARY "The left cell latch is open."
     --#ARGUMENTS {}
     --#SEVERITY WARNING
     --#TIMEINDEX 100
     --#STATE OPERATIONAL
::= 10060


hpevtDcnfgRightCellLatch TRAP-TYPE
     ENTERPRISE hpIpfE0Events
     VARIABLES { hpIpfEvtDetailStr }
     DESCRIPTION
        "The right ejector latch on the specified cell board is open."

     --#SUMMARY "Right ejector latch is open"
     --#ARGUMENTS {}
     --#SEVERITY WARNING
     --#TIMEINDEX 100
     --#STATE OPERATIONAL
::= 10061


hpevtCellLatchSensorBad TRAP-TYPE
     ENTERPRISE hpIpfE0Events
     VARIABLES { hpIpfEvtDetailStr }
     DESCRIPTION
        "The optical emitters on the cell latch sensors are not functioning."

     --#SUMMARY "The optical emitters on the cell latch sensors are not functioning"
     --#ARGUMENTS {}
     --#SEVERITY WARNING
     --#TIMEINDEX 100
     --#STATE OPERATIONAL
::= 10062


hpevtVrmVltFault TRAP-TYPE
     ENTERPRISE hpIpfE0Events
     VARIABLES { hpIpfEvtDetailStr }
     DESCRIPTION
        "The specified vrm is reporting a fault."

     --#SUMMARY "The vrm on the specified cell is reporting a voltage fault."
     --#ARGUMENTS {}
     --#SEVERITY WARNING
     --#TIMEINDEX 100
     --#STATE OPERATIONAL
::= 10063


hpevtVrmTempFlt TRAP-TYPE
     ENTERPRISE hpIpfE0Events
     VARIABLES { hpIpfEvtDetailStr }
     DESCRIPTION
        "The specified vrm is reporting a fault."

     --#SUMMARY "The vrm on the specified cell is reporting a temperature fault."
     --#ARGUMENTS {}
     --#SEVERITY WARNING
     --#TIMEINDEX 100
     --#STATE OPERATIONAL
::= 10064


hpevtVrmFlt TRAP-TYPE
     ENTERPRISE hpIpfE0Events
     VARIABLES { hpIpfEvtDetailStr }
     DESCRIPTION
        "The specified rail is reporting a fault."

     --#SUMMARY "The rail on a cell is reporting a fault."
     --#ARGUMENTS {}
     --#SEVERITY WARNING
     --#TIMEINDEX 100
     --#STATE OPERATIONAL
::= 10065


hpevtVrmIoVltFlt TRAP-TYPE
     ENTERPRISE hpIpfE0Events
     VARIABLES { hpIpfEvtDetailStr }
     DESCRIPTION
        "The specified pci vrm is reporting a voltage fault."

     --#SUMMARY "A I/O backplane vrm is reporting a voltage fault."
     --#ARGUMENTS {}
     --#SEVERITY WARNING
     --#TIMEINDEX 100
     --#STATE OPERATIONAL
::= 10068


hpevtPwrBrickVltFlt TRAP-TYPE
     ENTERPRISE hpIpfE0Events
     VARIABLES { hpIpfEvtDetailStr }
     DESCRIPTION
        "The specified pci power brick is reporting a voltage fault."

     --#SUMMARY "A I/O backplane power brick is reporting a voltage fault."
     --#ARGUMENTS {}
     --#SEVERITY WARNING
     --#TIMEINDEX 100
     --#STATE OPERATIONAL
::= 10069


hpevtVrmBkPlaneTempFlt TRAP-TYPE
     ENTERPRISE hpIpfE0Events
     VARIABLES { hpIpfEvtDetailStr }
     DESCRIPTION
        "The specified vrm is reporting a temperature fault."

     --#SUMMARY "A I/O backplane vrm is reporting a temperature fault."
     --#ARGUMENTS {}
     --#SEVERITY WARNING
     --#TIMEINDEX 100
     --#STATE OPERATIONAL
::= 10070


hpevtBkPlanePwrBrickTempFlt TRAP-TYPE
     ENTERPRISE hpIpfE0Events
     VARIABLES { hpIpfEvtDetailStr }
     DESCRIPTION
        "The specified pci power brick is reporting a temperature fault."

     --#SUMMARY "A I/O backplane power brick is reporting a temperature fault."
     --#ARGUMENTS {}
     --#SEVERITY WARNING
     --#TIMEINDEX 100
     --#STATE OPERATIONAL
::= 10071


hpevtBkPlanVrmRailFlt TRAP-TYPE
     ENTERPRISE hpIpfE0Events
     VARIABLES { hpIpfEvtDetailStr }
     DESCRIPTION
        "The specified vrm rail is reporting a fault."

     --#SUMMARY "A I/O backplane vrm rail is reporting a fault."
     --#ARGUMENTS {}
     --#SEVERITY WARNING
     --#TIMEINDEX 100
     --#STATE OPERATIONAL
::= 10072


hpevtBkPlanePwrBrkFlt TRAP-TYPE
     ENTERPRISE hpIpfE0Events
     VARIABLES { hpIpfEvtDetailStr }
     DESCRIPTION
        "The specified pci brick is reporting a fault."

     --#SUMMARY "A I/O backplane power brick is reporting a rail fault."
     --#ARGUMENTS {}
     --#SEVERITY WARNING
     --#TIMEINDEX 100
     --#STATE OPERATIONAL
::= 10073


hpevtBkPlaneVrmVltFlt TRAP-TYPE
     ENTERPRISE hpIpfE0Events
     VARIABLES { hpIpfEvtDetailStr }
     DESCRIPTION
        "The specified system backplane vrm is reporting a module voltage fault."

     --#SUMMARY "The specified system backplane vrm is reporting a module voltage fault."
     --#ARGUMENTS {}
     --#SEVERITY WARNING
     --#TIMEINDEX 100
     --#STATE OPERATIONAL
::= 10103


hpevtBkPlaneVrmTempFlt TRAP-TYPE
     ENTERPRISE hpIpfE0Events
     VARIABLES { hpIpfEvtDetailStr }
     DESCRIPTION
        "The specified system backplane vrm is reporting a temperature fault."

     --#SUMMARY "The specified system backplane vrm is reporting a temperature fault."
     --#ARGUMENTS {}
     --#SEVERITY WARNING
     --#TIMEINDEX 100
     --#STATE OPERATIONAL
::= 10104


hpevtBkPlaneFlt TRAP-TYPE
     ENTERPRISE hpIpfE0Events
     VARIABLES { hpIpfEvtDetailStr }
     DESCRIPTION
        "The specifed system backplane rail is reporting a fault"

     --#SUMMARY "The specifed system backplane rail is reporting a fault"
     --#ARGUMENTS {}
     --#SEVERITY WARNING
     --#TIMEINDEX 100
     --#STATE OPERATIONAL
::= 10105


hpevtMstrMpFailed TRAP-TYPE
     ENTERPRISE hpIpfE0Events
     VARIABLES { hpIpfEvtDetailStr }
     DESCRIPTION
        "The master mp has failed.  The slave has taken over management of the cabinet."

     --#SUMMARY "Master MP failure. Slave MP has taken control"
     --#ARGUMENTS {}
     --#SEVERITY WARNING
     --#TIMEINDEX 100
     --#STATE OPERATIONAL
::= 10115


hpevtNvramAlloc TRAP-TYPE
     ENTERPRISE hpIpfE0Events
     VARIABLES { hpIpfEvtDetailStr }
     DESCRIPTION
        "The NVRAM service was unable to satisfy an NVRAM allocation request."

     --#SUMMARY "The NVRAM service was unable to satisfy an NVRAM allocation request"
     --#ARGUMENTS {}
     --#SEVERITY CRITICAL
     --#TIMEINDEX 100
     --#STATE OPERATIONAL
::= 10116


hpevtRtcTimeReg TRAP-TYPE
     ENTERPRISE hpIpfE0Events
     VARIABLES { hpIpfEvtDetailStr }
     DESCRIPTION
        "The RTC seems to not be updating its internal time registers.  The cell cannot boot without the RTC."

     --#SUMMARY "The RTC not updating its internal time registers"
     --#ARGUMENTS {}
     --#SEVERITY CRITICAL
     --#TIMEINDEX 100
     --#STATE OPERATIONAL
::= 10132


hpevtPAAFltMx2 TRAP-TYPE
     ENTERPRISE hpIpfE0Events
     VARIABLES { hpIpfEvtDetailStr }
     DESCRIPTION
        "An uncorrectable Power Aware Architecture (PAA) fault has occurred on the MX2 module and PAA firmware has halted.  The system will continue to run without PAA firmware."

     --#SUMMARY "Uncorrectable PAA fault on MX2"
     --#ARGUMENTS {}
     --#SEVERITY WARNING
     --#TIMEINDEX 100
     --#STATE OPERATIONAL
::= 10159


hpevtAPIopenLnkLocCell TRAP-TYPE
     ENTERPRISE hpIpfE0Events
     VARIABLES { hpIpfEvtDetailStr }
     DESCRIPTION
        "fabric API is about to open the a link going out of the local cell"

     --#SUMMARY "fabric API is about to open the a link going out of the local cell"
     --#ARGUMENTS {}
     --#SEVERITY WARNING
     --#TIMEINDEX 100
     --#STATE OPERATIONAL
::= 10209


hpevtCSRreadUnsuccessTimeOut TRAP-TYPE
     ENTERPRISE hpIpfE0Events
     VARIABLES { hpIpfEvtDetailStr }
     DESCRIPTION
        "An Arches fabric CSR read was unsuccessful because of a timeout."

     --#SUMMARY "An Arches fabric CSR read was unsuccessful because of a timeout."
     --#ARGUMENTS {}
     --#SEVERITY CRITICAL
     --#TIMEINDEX 100
     --#STATE OPERATIONAL
::= 10272


hpevtCSRWriteUnsuccess TRAP-TYPE
     ENTERPRISE hpIpfE0Events
     VARIABLES { hpIpfEvtDetailStr }
     DESCRIPTION
        "An Arches fabric CSR write was unsuccessful"

     --#SUMMARY "An Arches fabric CSR write was unsuccessful."
     --#ARGUMENTS {}
     --#SEVERITY CRITICAL
     --#TIMEINDEX 100
     --#STATE OPERATIONAL
::= 10273


hpevtDataErrEncount TRAP-TYPE
     ENTERPRISE hpIpfE0Events
     VARIABLES { hpIpfEvtDetailStr }
     DESCRIPTION
        "The event data details the error return status from Phase3BackToBackPrep.  Internal debug only, this refers to an unexpected firmware error or data corruption."

     --#SUMMARY "The event data details the error that was encountered"
     --#ARGUMENTS {}
     --#SEVERITY CRITICAL
     --#TIMEINDEX 100
     --#STATE OPERATIONAL
::= 10343


hpevtConfigMaxMemory TRAP-TYPE
     ENTERPRISE hpIpfE0Events
     VARIABLES { hpIpfEvtDetailStr }
     DESCRIPTION
        "The maximum memory supported by this system has been exceeded.  The data field contains the amount of memory supported by the system."

     --#SUMMARY "The maximum memory supported by this system has been exceeded."
     --#ARGUMENTS {}
     --#SEVERITY CRITICAL
     --#TIMEINDEX 100
     --#STATE OPERATIONAL
::= 10351


hpevtFailDelBadPort TRAP-TYPE
     ENTERPRISE hpIpfE0Events
     VARIABLES { hpIpfEvtDetailStr }
     DESCRIPTION
        "Failed to delete a bad port while routing the fabric.  Data field indicates return status"

     --#SUMMARY "Failed to delete a bad port while routing the fabric.  Data field indicates return status."
     --#ARGUMENTS {}
     --#SEVERITY WARNING
     --#TIMEINDEX 100
     --#STATE OPERATIONAL
::= 10357


hpevtFailDelBadEdge TRAP-TYPE
     ENTERPRISE hpIpfE0Events
     VARIABLES { hpIpfEvtDetailStr }
     DESCRIPTION
        "failed to delete an edge that was found to be bad during routing"

     --#SUMMARY "Failed to delete an edge that was found to be bad during routing."
     --#ARGUMENTS {}
     --#SEVERITY WARNING
     --#TIMEINDEX 100
     --#STATE OPERATIONAL
::= 10358


hpevtCommandMemBuf TRAP-TYPE
     ENTERPRISE hpIpfE0Events
     VARIABLES { hpIpfEvtDetailStr }
     DESCRIPTION
        "A command to the memory buffer chip failed to complete."

     --#SUMMARY "A command to the memory buffer chip failed to complete."
     --#ARGUMENTS {}
     --#SEVERITY CRITICAL
     --#TIMEINDEX 100
     --#STATE OPERATIONAL
::= 10361


hpevtUnsupprtArflsCsrRouteTravsble TRAP-TYPE
     ENTERPRISE hpIpfE0Events
     VARIABLES { hpIpfEvtDetailStr }
     DESCRIPTION
        "The Arches Fabric function ArfIsCsrRouteTraversable was called for a back-to-back system.  This is unsupported, ArfIsCsrRouteTraversable should only be called for systems with crossbars.  No data."

     --#SUMMARY "The Arches Fabric function ArfIsCsrRouteTraversable was called for a back-to-back system.  This is unsupported, ArfIsCsrRouteTraversable should only be called for systems with crossbars.  No data."
     --#ARGUMENTS {}
     --#SEVERITY WARNING
     --#TIMEINDEX 100
     --#STATE OPERATIONAL
::= 10375


hpevtInvalidPortToTravsble TRAP-TYPE
     ENTERPRISE hpIpfE0Events
     VARIABLES { hpIpfEvtDetailStr }
     DESCRIPTION
        "An invalid port number was given as an input to an Arches Fabric Traversability function.  The port is expected to be an internal XBC num (8-15), but the actual port was not.  Data field: (XBC number << 32) | (port number << 48)"

     --#SUMMARY "An invalid port number was given as an input to an Arches Fabric Traversability function.  The port is expected to be an internal XBC num (8-15), but the actual port was not.  Data field: (XBC number  32) | (port number 48)."
     --#ARGUMENTS {}
     --#SEVERITY WARNING
     --#TIMEINDEX 100
     --#STATE OPERATIONAL
::= 10376


hpevtUnbleRdXBCPortNghbr TRAP-TYPE
     ENTERPRISE hpIpfE0Events
     VARIABLES { hpIpfEvtDetailStr }
     DESCRIPTION
        "Unable to read XBC port neighbor information.
Data field: (xbcNum << 32) | (portNum << 48)"

     --#SUMMARY "Unable to read XBC port neighbor information.  Data field: (xbcNum  32) | (portNum  48)."
     --#ARGUMENTS {}
     --#SEVERITY WARNING
     --#TIMEINDEX 100
     --#STATE OPERATIONAL
::= 10377


hpevtXBCPortUnexpctNghbrChip TRAP-TYPE
     ENTERPRISE hpIpfE0Events
     VARIABLES { hpIpfEvtDetailStr }
     DESCRIPTION
        "XBC port with an unexpected neighbor chip type.
Data field: (expected chip type) | (actual chip type << 16) | (xbcNum << 32) |
                 (portNum << 48)"

     --#SUMMARY "XBC port with an unexpected neighbor chip type.  Data field: (expected chip type) | (actual chip type  16) | (xbcNum  32) |(portNum  48)."
     --#ARGUMENTS {}
     --#SEVERITY WARNING
     --#TIMEINDEX 100
     --#STATE OPERATIONAL
::= 10378


hpevtXBCPortHaveUnxpctNghbrID TRAP-TYPE
     ENTERPRISE hpIpfE0Events
     VARIABLES { hpIpfEvtDetailStr }
     DESCRIPTION
        "An XBC port was found to have an unexpected neighbor ID.
Data field: (expected NID) | (actual NID << 16) | (xbcNum << 32) | (portNum << 48)"

     --#SUMMARY "An XBC port was found to have an unexpected neighbor ID.  Data field: (expected NID) | (actual NID  16) | (xbcNum  32) | (portNum  48)"
     --#ARGUMENTS {}
     --#SEVERITY WARNING
     --#TIMEINDEX 100
     --#STATE OPERATIONAL
::= 10379


hpevtXBCHaveUnexpctNghbrPrtConn TRAP-TYPE
     ENTERPRISE hpIpfE0Events
     VARIABLES { hpIpfEvtDetailStr }
     DESCRIPTION
        "An XBC was found to have an unexpected neighbor port connection.
Data field: (expected port) | (actual port << 16) | (xbcNum << 32) | (portNum << 48)"

     --#SUMMARY "An XBC was found to have an unexpected neighbor port connection.  Data field: (expected port) | (actual port  16) | (xbcNum  32) | (portNum  48)"
     --#ARGUMENTS {}
     --#SEVERITY WARNING
     --#TIMEINDEX 100
     --#STATE OPERATIONAL
::= 10380


hpevtDataNotFndEdgLst TRAP-TYPE
     ENTERPRISE hpIpfE0Events
     VARIABLES { hpIpfEvtDetailStr }
     DESCRIPTION
        "The expected data was not found in the Arches Fabric expected edge list.
Data field is unused"

     --#SUMMARY "The expected data was not found in the Arches Fabric expected edge list.  Data field is unused."
     --#ARGUMENTS {}
     --#SEVERITY WARNING
     --#TIMEINDEX 100
     --#STATE OPERATIONAL
::= 10381


hpevtXBCPrtUnxpctNgbrChip TRAP-TYPE
     ENTERPRISE hpIpfE0Events
     VARIABLES { hpIpfEvtDetailStr }
     DESCRIPTION
        "An XBC port has an unexpected neighbor chip type.
Data field: neighbor type found, bits [7:0], other bits unused"

     --#SUMMARY "An XBC port has an unexpected neighbor chip type.  Data field: neighbor type found."
     --#ARGUMENTS {}
     --#SEVERITY WARNING
     --#TIMEINDEX 100
     --#STATE OPERATIONAL
::= 10382


hpevtXBCtoXBCLnkDwn TRAP-TYPE
     ENTERPRISE hpIpfE0Events
     VARIABLES { hpIpfEvtDetailStr }
     DESCRIPTION
        "A previously good XBC-XBC link was found to be down.
Data field: (xbcNum << 32) | (portNum << 48)"

     --#SUMMARY "A previously good XBC-XBC link was found to be down.  Data field: (xbcNum  32) | (portNum  48)."
     --#ARGUMENTS {}
     --#SEVERITY WARNING
     --#TIMEINDEX 100
     --#STATE OPERATIONAL
::= 10384


hpevtXBCprtFndErrTravsbl TRAP-TYPE
     ENTERPRISE hpIpfE0Events
     VARIABLES { hpIpfEvtDetailStr }
     DESCRIPTION
        "An XBC port was found to have a Fatal Error during traversability test.
Data field: (xbcNum << 32) | (portNum << 48)"

     --#SUMMARY "An XBC port was found to have a Fatal Error during traversability test.  Data field: (xbcNum  32) | (portNum  48)."
     --#ARGUMENTS {}
     --#SEVERITY WARNING
     --#TIMEINDEX 100
     --#STATE OPERATIONAL
::= 10385


hpevtUnblRdLnkCelFabCSR TRAP-TYPE
     ENTERPRISE hpIpfE0Events
     VARIABLES { hpIpfEvtDetailStr }
     DESCRIPTION
        "Unable to read the local cell's LINK_SEL_FABRIC CSR
Data field: unused"

     --#SUMMARY "Unable to read the local cell's LINK_SEL_FABRIC CSR.  Data field: unused"
     --#ARGUMENTS {}
     --#SEVERITY WARNING
     --#TIMEINDEX 100
     --#STATE OPERATIONAL
::= 10386


hpevtUblRdXBCrouteTbl TRAP-TYPE
     ENTERPRISE hpIpfE0Events
     VARIABLES { hpIpfEvtDetailStr }
     DESCRIPTION
        "Unable to read the XBC route table.
Data field: (route index) | (xbcNum << 32) | (portNum << 48)"

     --#SUMMARY "Unable to read the XBC route table.  Data field: (route index) | (xbcNum  32) | (portNum  48)."
     --#ARGUMENTS {}
     --#SEVERITY WARNING
     --#TIMEINDEX 100
     --#STATE OPERATIONAL
::= 10387


hpevtXBCLnkNotConnCSRTravsbl TRAP-TYPE
     ENTERPRISE hpIpfE0Events
     VARIABLES { hpIpfEvtDetailStr }
     DESCRIPTION
        "An XBC link was found to be not connected while testing CSR traffic traversability.  Data field: (xbcNum << 32) | (portNum << 48)"

     --#SUMMARY "An XBC link was found to be not connected while testing CSR traffic traversability.  Data field: (xbcNum  32) | (portNum  48)."
     --#ARGUMENTS {}
     --#SEVERITY WARNING
     --#TIMEINDEX 100
     --#STATE OPERATIONAL
::= 10388


hpevtErrRdAlrecAlbIdCsr TRAP-TYPE
     ENTERPRISE hpIpfE0Events
     VARIABLES { hpIpfEvtDetailStr }
     DESCRIPTION
        "Error reading Skyline ALREC_ALB_ID CSR
Data field: (Skyline port) | (Cell number << 56)"

     --#SUMMARY "Error reading Skyline ALREC_ALB_ID CSR.  Data field: (Skyline port) | (Cell number  56)."
     --#ARGUMENTS {}
     --#SEVERITY WARNING
     --#TIMEINDEX 100
     --#STATE OPERATIONAL
::= 10389


hpevtCirRoutFndTstXbcCsr TRAP-TYPE
     ENTERPRISE hpIpfE0Events
     VARIABLES { hpIpfEvtDetailStr }
     DESCRIPTION
        "A circular route was found while testing XBC CSR traffic traversability.
Data field: (target XBC << 32)  | (cellNum << 56)"

     --#SUMMARY "A circular route was found while testing XBC CSR traffic traversability.  Data field: (target XBC  32)  | (cellNum  56)."
     --#ARGUMENTS {}
     --#SEVERITY WARNING
     --#TIMEINDEX 100
     --#STATE OPERATIONAL
::= 10390


hpevtXBCRdErrAlrecAlbIdCsr TRAP-TYPE
     ENTERPRISE hpIpfE0Events
     VARIABLES { hpIpfEvtDetailStr }
     DESCRIPTION
        "Error reading ALREC_ALB_ID CSR for an XBC port.
Data field: (xbcNum << 32) | (portNum << 48)"

     --#SUMMARY "Error reading ALREC_ALB_ID CSR for an XBC port.  Data field: (xbcNum  32) | (portNum  48)."
     --#ARGUMENTS {}
     --#SEVERITY WARNING
     --#TIMEINDEX 100
     --#STATE OPERATIONAL
::= 10391


hpevtXBC-XBCPrtHavInvldChipCnn TRAP-TYPE
     ENTERPRISE hpIpfE0Events
     VARIABLES { hpIpfEvtDetailStr }
     DESCRIPTION
        "An XBC-XBC port had an invalid chip type connection.
Data field: (expected chip type) | (actual chip type << 32)"

     --#SUMMARY "An XBC-XBC port had an invalid chip type connection.  Data field: (expected chip type) | (actual chip type  32)."
     --#ARGUMENTS {}
     --#SEVERITY WARNING
     --#TIMEINDEX 100
     --#STATE OPERATIONAL
::= 10392


hpevtArflsXbcRotTravrsblCalBakToBak TRAP-TYPE
     ENTERPRISE hpIpfE0Events
     VARIABLES { hpIpfEvtDetailStr }
     DESCRIPTION
        "ArfIsXbcRouteTraversable was called on a back-to-back system which is an improper use of the function.  Data field: unused"

     --#SUMMARY "ArfIsXbcRouteTraversable was called on a back-to-back system which is an improper use of the function.  Data field: unused"
     --#ARGUMENTS {}
     --#SEVERITY WARNING
     --#TIMEINDEX 100
     --#STATE OPERATIONAL
::= 10393


hpevtXBCToXBClnkFndFatErr TRAP-TYPE
     ENTERPRISE hpIpfE0Events
     VARIABLES { hpIpfEvtDetailStr }
     DESCRIPTION
        "In ArfIsXbcRouteTraversable, an XBC-XBC link was found to have fatal errors.
Data field: (xbcNum << 32) | (portNum << 48)"

     --#SUMMARY "In ArfIsXbcRouteTraversable, an XBC-XBC link was found to have fatal errors.  Data field: (xbcNum  32) | (portNum  48)."
     --#ARGUMENTS {}
     --#SEVERITY WARNING
     --#TIMEINDEX 100
     --#STATE OPERATIONAL
::= 10394


hpevtUnablRdXbcRotTblEnblMskCsr TRAP-TYPE
     ENTERPRISE hpIpfE0Events
     VARIABLES { hpIpfEvtDetailStr }
     DESCRIPTION
        "Unable to read the XBC ROUTE_TABLE_ENABLE_MASK CSR.
Data field: (xbcNum << 32) | (portNum << 48)"

     --#SUMMARY "Unable to read the XBC ROUTE_TABLE_ENABLE_MASK CSR.  Data field: (xbcNum  32) | (portNum  48)."
     --#ARGUMENTS {}
     --#SEVERITY WARNING
     --#TIMEINDEX 100
     --#STATE OPERATIONAL
::= 10395


hpevtErrRdXbcRotTablCsr TRAP-TYPE
     ENTERPRISE hpIpfE0Events
     VARIABLES { hpIpfEvtDetailStr }
     DESCRIPTION
        "Error reading an XBC ROUTE_TABLE CSR.
Data field: route index | (xbcNum << 32) | (portNum << 48)"

     --#SUMMARY "Error reading an XBC ROUTE_TABLE CSR.  Data field: route index | (xbcNum  32) | (portNum  48)."
     --#ARGUMENTS {}
     --#SEVERITY WARNING
     --#TIMEINDEX 100
     --#STATE OPERATIONAL
::= 10396


hpevtXbcPrtErrRdAlrecAlbIDCsr TRAP-TYPE
     ENTERPRISE hpIpfE0Events
     VARIABLES { hpIpfEvtDetailStr }
     DESCRIPTION
        "Error reading ALB ALREC_ALB_ID CSR for an XBC port.
Data field: (xbcNum << 32) | (portNum << 48)"

     --#SUMMARY "Error reading ALB ALREC_ALB_ID CSR for an XBC port.  Data field: (xbcNum  32) | (portNum  48)."
     --#ARGUMENTS {}
     --#SEVERITY WARNING
     --#TIMEINDEX 100
     --#STATE OPERATIONAL
::= 10397


hpevtXbcPrtFndUnxpctNgbrChip TRAP-TYPE
     ENTERPRISE hpIpfE0Events
     VARIABLES { hpIpfEvtDetailStr }
     DESCRIPTION
        "An XBC port was found with an unexpected neighbor chip.
Data field: expected chip type | (actual chip type << 32)"

     --#SUMMARY "An XBC port was found with an unexpected neighbor chip.  Data field: expected chip type | (actual chip type  32)."
     --#ARGUMENTS {}
     --#SEVERITY WARNING
     --#TIMEINDEX 100
     --#STATE OPERATIONAL
::= 10398


hpevtCelPrtPairNotFndGrphDat TRAP-TYPE
     ENTERPRISE hpIpfE0Events
     VARIABLES { hpIpfEvtDetailStr }
     DESCRIPTION
        "A cell/port pair was not found in the expected graph data.
Data field: (cellNum << 32) | CC portNum"

     --#SUMMARY "A cell/port pair was not found in the expected graph data.  Data field: (cellNum  32) | CC portNum."
     --#ARGUMENTS {}
     --#SEVERITY WARNING
     --#TIMEINDEX 100
     --#STATE OPERATIONAL
::= 10401


hpevtArchFabFndLocCelLnkNotConn TRAP-TYPE
     ENTERPRISE hpIpfE0Events
     VARIABLES { hpIpfEvtDetailStr }
     DESCRIPTION
        "Arches Fabric Traversability code unexpectedly found the local cell link not connected.  Data field: linkState (0 = connected, 1 = link pending, 2 = not connected, -1 = error)"

     --#SUMMARY "Arches Fabric Traversability code unexpectedly found the local cell link not connected.  Data field: linkState (0 = connected, 1 = link pending, 2 = not connected, -1 = error)"
     --#ARGUMENTS {}
     --#SEVERITY WARNING
     --#TIMEINDEX 100
     --#STATE OPERATIONAL
::= 10402


hpevtXbcErrRdRoutCsr TRAP-TYPE
     ENTERPRISE hpIpfE0Events
     VARIABLES { hpIpfEvtDetailStr }
     DESCRIPTION
        "Error reading the ROUTEx CSR on the XBC.
Data field: route index | (xbcNum << 32) | (portNum << 48)"

     --#SUMMARY "Error reading the ROUTEx CSR on the XBC.  Data field: route index | (xbcNum  32) | (portNum  48)."
     --#ARGUMENTS {}
     --#SEVERITY WARNING
     --#TIMEINDEX 100
     --#STATE OPERATIONAL
::= 10403


hpevtXbcUnablRdAlrecAlbIdCsr TRAP-TYPE
     ENTERPRISE hpIpfE0Events
     VARIABLES { hpIpfEvtDetailStr }
     DESCRIPTION
        "Unable to read the ALB ALREC_ALB_ID CSR for an XBC port.
Data field: (xbcNum << 32) | (portNum << 48)"

     --#SUMMARY "Unable to read the ALB ALREC_ALB_ID CSR for an XBC port.  Data field: (xbcNum  32) | (portNum  48)."
     --#ARGUMENTS {}
     --#SEVERITY WARNING
     --#TIMEINDEX 100
     --#STATE OPERATIONAL
::= 10404


hpevtXbcPrtHasUnxpctNgbrChptype TRAP-TYPE
     ENTERPRISE hpIpfE0Events
     VARIABLES { hpIpfEvtDetailStr }
     DESCRIPTION
        "An XBC port has an unexpected neighbor chip type.
Data field: expected neighbor chip type | (actual neighbor chip type << 32)"

     --#SUMMARY "An XBC port has an unexpected neighbor chip type.  Data field: expected neighbor chip type | (actual neighbor chip type  32)."
     --#ARGUMENTS {}
     --#SEVERITY WARNING
     --#TIMEINDEX 100
     --#STATE OPERATIONAL
::= 10405


hpevtCelToCelLnkHasUnxpctNgbrChpType TRAP-TYPE
     ENTERPRISE hpIpfE0Events
     VARIABLES { hpIpfEvtDetailStr }
     DESCRIPTION
        "A Cell-Cell link has an unexpected neighbor chip type.
Data field: expected neighbor chip type | (actual neighbor chip type << 32)"

     --#SUMMARY "A Cell-Cell link has an unexpected neighbor chip type.  Data field: expected neighbor chip type | (actual neighbor chip type  32)."
     --#ARGUMENTS {}
     --#SEVERITY WARNING
     --#TIMEINDEX 100
     --#STATE OPERATIONAL
::= 10406


hpevtCelPrtPairNotExstGrphDat TRAP-TYPE
     ENTERPRISE hpIpfE0Events
     VARIABLES { hpIpfEvtDetailStr }
     DESCRIPTION
        "The cell/port pair does not exist in the Arches Fabric expected graph data.
Data field: CC port | (cellNum << 32)"

     --#SUMMARY "The cell/port pair does not exist in the Arches Fabric expected graph data.  Data field: CC port | (cellNum  32)."
     --#ARGUMENTS {}
     --#SEVERITY WARNING
     --#TIMEINDEX 100
     --#STATE OPERATIONAL
::= 10407


hpevtCelToCelLnkConnUnxpctNgbrPrt TRAP-TYPE
     ENTERPRISE hpIpfE0Events
     VARIABLES { hpIpfEvtDetailStr }
     DESCRIPTION
        "A Cell-Cell link is connected to an unexpected neighbor port.
Data field: expected neighbor port | (actual neighbor port << 32)"

     --#SUMMARY "A Cell-Cell link is connected to an unexpected neighbor port.  Data field: expected neighbor port | (actual neighbor port  32)."
     --#ARGUMENTS {}
     --#SEVERITY WARNING
     --#TIMEINDEX 100
     --#STATE OPERATIONAL
::= 10408


hpevtCelToCelLnkConnUnxpctCel TRAP-TYPE
     ENTERPRISE hpIpfE0Events
     VARIABLES { hpIpfEvtDetailStr }
     DESCRIPTION
        "A Cell-Cell link is connected to an unexpected cell.
Data field: expected neighbor ID | (actual neighbor ID << 16) | (target cell << 32) | (local cell << 48)"

     --#SUMMARY "A Cell-Cell link is connected to an unexpected cell.  Data field: expected neighbor ID | (actual neighbor ID  16) | (target cell  32) | (local cell  48)."
     --#ARGUMENTS {}
     --#SEVERITY WARNING
     --#TIMEINDEX 100
     --#STATE OPERATIONAL
::= 10409


hpevtEFIDrvrFailLoad TRAP-TYPE
     ENTERPRISE hpIpfE0Events
     VARIABLES { hpIpfEvtDetailStr }
     DESCRIPTION
        "An EFI Driver may be corrupt."

     --#SUMMARY "An EFI driver failed to load."
     --#ARGUMENTS {}
     --#SEVERITY WARNING
     --#TIMEINDEX 100
     --#STATE OPERATIONAL
::= 10412


hpevtVmRetErrNonCohTbl TRAP-TYPE
     ENTERPRISE hpIpfE0Events
     VARIABLES { hpIpfEvtDetailStr }
     DESCRIPTION
        "VM_FindAllRoutes returned an unexpected error duing Non-Coherent table setup.  Data field: (return value) | (source cell << 32) | (target cell << 48)"

     --#SUMMARY "VM_FindAllRoutes returned an unexpected error duing Non-Coherent table setup.  Data field: (return value) | (source cell  32) | (target cell  48)."
     --#ARGUMENTS {}
     --#SEVERITY WARNING
     --#TIMEINDEX 100
     --#STATE OPERATIONAL
::= 10413


hpevtNctTblWrtGlobLnkSelNonCohFail TRAP-TYPE
     ENTERPRISE hpIpfE0Events
     VARIABLES { hpIpfEvtDetailStr }
     DESCRIPTION
        "In SetupNCTable, a write to the GLOBAL_LINK_SEL_NONCOH CSR failed.
Data field: (data written to CSR) | (actual CSR data read << 32)"

     --#SUMMARY "In SetupNCTable, a write to the GLOBAL_LINK_SEL_NONCOH CSR failed.  Data field: (data written to CSR) | (actual CSR data read  32)."
     --#ARGUMENTS {}
     --#SEVERITY WARNING
     --#TIMEINDEX 100
     --#STATE OPERATIONAL
::= 10414


hpevtNctTblFailArfPhs3 TRAP-TYPE
     ENTERPRISE hpIpfE0Events
     VARIABLES { hpIpfEvtDetailStr }
     DESCRIPTION
        "SetupNCTable failed in ArfPhase3.
Data field: cell set passed in to SetupNCTable"

     --#SUMMARY "SetupNCTable failed in ArfPhase3.  Data field: cell set passed in to SetupNCTable"
     --#ARGUMENTS {}
     --#SEVERITY WARNING
     --#TIMEINDEX 100
     --#STATE OPERATIONAL
::= 10415


hpevtPostRndevzFailPrepBckToBckSys TRAP-TYPE
     ENTERPRISE hpIpfE0Events
     VARIABLES { hpIpfEvtDetailStr }
     DESCRIPTION
        "A failure occurred while prepping a back-to-back system for post-rendezvous Arches Fabric setup.  Data field: return value from Phase4BackToBackPrep"

     --#SUMMARY "A failure occurred while prepping a back-to-back system for post-rendezvous Arches Fabric setup.  Data field: return value from Phase4BackToBackPrep."
     --#ARGUMENTS {}
     --#SEVERITY WARNING
     --#TIMEINDEX 100
     --#STATE OPERATIONAL
::= 10427


hpevtArfPhs4UnablSetNonCohLnk TRAP-TYPE
     ENTERPRISE hpIpfE0Events
     VARIABLES { hpIpfEvtDetailStr }
     DESCRIPTION
        "ArfPhase4 was unable to set up the Non-Coherent lnk select to at least one cell in its alive/gsm sharing set.
Data field: bitmap of unreachable cells"

     --#SUMMARY "ArfPhase4 was unable to set up the Non-Coherent lnk select to at least one cell in its alive/gsm sharing set.  Data field: bitmap of unreachable cells."
     --#ARGUMENTS {}
     --#SEVERITY WARNING
     --#TIMEINDEX 100
     --#STATE OPERATIONAL
::= 10429


hpevtUnablSetNonCohRout TRAP-TYPE
     ENTERPRISE hpIpfE0Events
     VARIABLES { hpIpfEvtDetailStr }
     DESCRIPTION
        "Unable to set the Non-Coherent route.
Data field: (sourceCell << 32) | (cell set passed in to SetupNCTable)"

     --#SUMMARY "Unable to set the Non-Coherent route.  Data field: (sourceCell  32) | (cell set passed in to SetupNCTable)."
     --#ARGUMENTS {}
     --#SEVERITY WARNING
     --#TIMEINDEX 100
     --#STATE OPERATIONAL
::= 10431


hpevtUnableSetCohRoutCel TRAP-TYPE
     ENTERPRISE hpIpfE0Events
     VARIABLES { hpIpfEvtDetailStr }
     DESCRIPTION
        "Unable to setup the Coherent route table for a cell in our partition.
Data field: (sourceCell << 32) | (cell set passed in to SetupCohTable)"

     --#SUMMARY "Unable to setup the Coherent route table for a cell in our partition.  Data field: (sourceCell  32) | (cell set passed in to SetupCohTable)."
     --#ARGUMENTS {}
     --#SEVERITY WARNING
     --#TIMEINDEX 100
     --#STATE OPERATIONAL
::= 10432


hpevtErrWrtXbcRoutTblEnblMskCsr TRAP-TYPE
     ENTERPRISE hpIpfE0Events
     VARIABLES { hpIpfEvtDetailStr }
     DESCRIPTION
        "Error writing the XBC ROUTE_TABLE_ENABLE_MASK CSR.
Data field: (route set to disable) | (xbcNum << 32) | (xbc port << 48)"

     --#SUMMARY "Error writing the XBC ROUTE_TABLE_ENABLE_MASK CSR.  Data field: (route set to disable) | (xbcNum  32) | (xbc port  48)."
     --#ARGUMENTS {}
     --#SEVERITY WARNING
     --#TIMEINDEX 100
     --#STATE OPERATIONAL
::= 10435


hpevtVertxRetUnxpctErrNonCohTbl TRAP-TYPE
     ENTERPRISE hpIpfE0Events
     VARIABLES { hpIpfEvtDetailStr }
     DESCRIPTION
        "The Arches Fabric vertex module returned an unexpected error duing Non-Coherent table setup.
Data field: (return value) | (sourceCell << 32) | (dest cell << 48)"

     --#SUMMARY "The Arches Fabric vertex module returned an unexpected error duing Non-Coherent table setup. Data field: (return value) | (sourceCell  32) | (dest cell  48)."
     --#ARGUMENTS {}
     --#SEVERITY WARNING
     --#TIMEINDEX 100
     --#STATE OPERATIONAL
::= 10436


hpevtWrtSkyGlobLnkSelCohFail TRAP-TYPE
     ENTERPRISE hpIpfE0Events
     VARIABLES { hpIpfEvtDetailStr }
     DESCRIPTION
        "A write to a Skyline Global LINK_SEL_COHx CSR failed.
Data field: cell number of the Skyline that failed, bits [7:0]. Other bits unused"

     --#SUMMARY "A write to a Skyline Global LINK_SEL_COHx CSR failed.  Data field: cell number of the Skyline that failed."
     --#ARGUMENTS {}
     --#SEVERITY WARNING
     --#TIMEINDEX 100
     --#STATE OPERATIONAL
::= 10439


hpevtUnablWrtXbcPrtCsr TRAP-TYPE
     ENTERPRISE hpIpfE0Events
     VARIABLES { hpIpfEvtDetailStr }
     DESCRIPTION
        "Unable to write the XBC port scratch CSR with the routing state.
Data field: (routing state) | (xbcNum << 32) | (portNum << 48)"

     --#SUMMARY "Unable to write the XBC port scratch CSR with the routing state.  Data field: (routing state) | (xbcNum  32) | (portNum  48)."
     --#ARGUMENTS {}
     --#SEVERITY WARNING
     --#TIMEINDEX 100
     --#STATE OPERATIONAL
::= 10475


hpevtSysFwUnAccesComplxProf TRAP-TYPE
     ENTERPRISE hpIpfE0Events
     VARIABLES { hpIpfEvtDetailStr }
     DESCRIPTION
        "Couldn't get the configured set during Fabric Init"

     --#SUMMARY "System Firmware was unable to access the configured set stored in the complex profile."
     --#ARGUMENTS {}
     --#SEVERITY WARNING
     --#TIMEINDEX 100
     --#STATE OPERATIONAL
::= 10481


hpevtSysFwDetctErrFabInit TRAP-TYPE
     ENTERPRISE hpIpfE0Events
     VARIABLES { hpIpfEvtDetailStr }
     DESCRIPTION
        "Error while running the Arches Fabric API part of Fabric Init."

     --#SUMMARY "System Firmware detected an error during Fabric Init."
     --#ARGUMENTS {}
     --#SEVERITY WARNING
     --#TIMEINDEX 100
     --#STATE OPERATIONAL
::= 10482


hpevtSysFwDetctFailFabInit TRAP-TYPE
     ENTERPRISE hpIpfE0Events
     VARIABLES { hpIpfEvtDetailStr }
     DESCRIPTION
        "Failure while running the Fabric API part of Fabric Init."

     --#SUMMARY "System Firmware detected a failure during Fabric Init."
     --#ARGUMENTS {}
     --#SEVERITY WARNING
     --#TIMEINDEX 100
     --#STATE OPERATIONAL
::= 10483


hpevtSysFwDetctErrFabOptimz TRAP-TYPE
     ENTERPRISE hpIpfE0Events
     VARIABLES { hpIpfEvtDetailStr }
     DESCRIPTION
        "An error was encountered while running the Fabric API to optimize the fabric."

     --#SUMMARY "System Firmware detected an error during Fabric Optimize."
     --#ARGUMENTS {}
     --#SEVERITY WARNING
     --#TIMEINDEX 100
     --#STATE OPERATIONAL
::= 10487


hpevtInPwrUPSFail TRAP-TYPE
     ENTERPRISE hpIpfE0Events
     VARIABLES { hpIpfEvtDetailStr }
     DESCRIPTION
        "Input power to the specified UPS has failed."

     --#SUMMARY "Input power to the specified UPS has failed."
     --#ARGUMENTS {}
     --#SEVERITY WARNING
     --#TIMEINDEX 100
     --#STATE OPERATIONAL
::= 10489


hpevtUpsRestored TRAP-TYPE
     ENTERPRISE hpIpfE0Events
     VARIABLES { hpIpfEvtDetailStr }
     DESCRIPTION
        "Input power to the specified UPS has been restored."

     --#SUMMARY "Input power to the specified UPS has been restored."
     --#ARGUMENTS {}
     --#SEVERITY WARNING
     --#TIMEINDEX 100
     --#STATE OPERATIONAL
::= 10490


hpevtUpsExhausted TRAP-TYPE
     ENTERPRISE hpIpfE0Events
     VARIABLES { hpIpfEvtDetailStr }
     DESCRIPTION
        "The system is being powered down as UPS power is exhausted."

     --#SUMMARY "UPS power exhausted. The system is being powered down."
     --#ARGUMENTS {}
     --#SEVERITY CRITICAL
     --#TIMEINDEX 100
     --#STATE OPERATIONAL
::= 10495


hpevtSALFailRedzvsProcs TRAP-TYPE
     ENTERPRISE hpIpfE0Events
     VARIABLES { hpIpfEvtDetailStr }
     DESCRIPTION
        "During SAL Machine Check handling, SAL fail to round up all the processor
entering SAL Machine check handler."

     --#SUMMARY "During Machine Check handling, SAL failed to rendezvous all the processors."
     --#ARGUMENTS {}
     --#SEVERITY WARNING
     --#TIMEINDEX 100
     --#STATE OPERATIONAL
::= 10509


hpevtSALFailClrCECLog TRAP-TYPE
     ENTERPRISE hpIpfE0Events
     VARIABLES { hpIpfEvtDetailStr }
     DESCRIPTION
        "Sal failed to clear the CEC logs during Machine check handling.
The data field return an ASCII name of the CEC that failed to clear."

     --#SUMMARY "SAL failed to clear the CEC logs during Machine check handling."
     --#ARGUMENTS {}
     --#SEVERITY WARNING
     --#TIMEINDEX 100
     --#STATE OPERATIONAL
::= 10510


hpevtSysFwUnAccesXBCSemphr TRAP-TYPE
     ENTERPRISE hpIpfE0Events
     VARIABLES { hpIpfEvtDetailStr }
     DESCRIPTION
        "An error occurred while getting the XBC semaphore."

     --#SUMMARY "System FW was unable to access the XBC semaphore."
     --#ARGUMENTS {}
     --#SEVERITY WARNING
     --#TIMEINDEX 100
     --#STATE OPERATIONAL
::= 10516


hpevtSysFwDetctErrRelXBCGlobSemphr TRAP-TYPE
     ENTERPRISE hpIpfE0Events
     VARIABLES { hpIpfEvtDetailStr }
     DESCRIPTION
        "An error occurred while releasing the XBC Global Semaphore."

     --#SUMMARY "System Firmware detected an error while trying to release the XBC Global Semaphore."
     --#ARGUMENTS {}
     --#SEVERITY WARNING
     --#TIMEINDEX 100
     --#STATE OPERATIONAL
::= 10518


hpevtSysFwDetctErrOwnXBCGlobSemphr TRAP-TYPE
     ENTERPRISE hpIpfE0Events
     VARIABLES { hpIpfEvtDetailStr }
     DESCRIPTION
        "An error occurred while checking the owner of the XBC Global Semaphore."

     --#SUMMARY "System Firmware detected an Error while checking the owner of the XBC Global Semaphore."
     --#ARGUMENTS {}
     --#SEVERITY WARNING
     --#TIMEINDEX 100
     --#STATE OPERATIONAL
::= 10519


hpevtErrFormXbcSemphrAddr TRAP-TYPE
     ENTERPRISE hpIpfE0Events
     VARIABLES { hpIpfEvtDetailStr }
     DESCRIPTION
        "An error occurred while forming the XBC semaphore address.  Data Field: (xbc << 32) | (cell << 56)"

     --#SUMMARY "An error occurred while forming the XBC semaphore address"
     --#ARGUMENTS {}
     --#SEVERITY WARNING
     --#TIMEINDEX 100
     --#STATE OPERATIONAL
::= 10520


hpevtErrRdXbcGlobSemphr TRAP-TYPE
     ENTERPRISE hpIpfE0Events
     VARIABLES { hpIpfEvtDetailStr }
     DESCRIPTION
        "Error reading the XBC Global Semaphore.  Data Field: (cell num << 56) | (xbc << 32)"

     --#SUMMARY "Error reading the XBC Global Semaphore"
     --#ARGUMENTS {}
     --#SEVERITY WARNING
     --#TIMEINDEX 100
     --#STATE OPERATIONAL
::= 10521


hpevtFailGetXbcGlobSemphrAddr TRAP-TYPE
     ENTERPRISE hpIpfE0Events
     VARIABLES { hpIpfEvtDetailStr }
     DESCRIPTION
        "Failure to get the XBC Global Semaphore address.  Data Field: (cell num << 56) | (xbc << 32)"

     --#SUMMARY "Failure to get the XBC Global Semaphore address"
     --#ARGUMENTS {}
     --#SEVERITY WARNING
     --#TIMEINDEX 100
     --#STATE OPERATIONAL
::= 10523


hpevtFailWrtXbcGlobSemphr TRAP-TYPE
     ENTERPRISE hpIpfE0Events
     VARIABLES { hpIpfEvtDetailStr }
     DESCRIPTION
        "Failed to write the XBC Global Semaphore.  Data Field: (cell num << 56) | (xbc << 32)"

     --#SUMMARY "Failed to write the XBC Global Semaphore."
     --#ARGUMENTS {}
     --#SEVERITY WARNING
     --#TIMEINDEX 100
     --#STATE OPERATIONAL
::= 10524


hpevtFailRdXbcGlobSemphr TRAP-TYPE
     ENTERPRISE hpIpfE0Events
     VARIABLES { hpIpfEvtDetailStr }
     DESCRIPTION
        "Failed to read the XBC Global Semaphore.  Data Field: (cell num << 56) | (xbc << 32)"

     --#SUMMARY "Failed to read the XBC Global Semaphore"
     --#ARGUMENTS {}
     --#SEVERITY WARNING
     --#TIMEINDEX 100
     --#STATE OPERATIONAL
::= 10528


hpevtFailGetAddrXbcGlobSemphr TRAP-TYPE
     ENTERPRISE hpIpfE0Events
     VARIABLES { hpIpfEvtDetailStr }
     DESCRIPTION
        "Failed to get the address of the XBC Global Semaphore.  Data Field: (cell num << 56) | (xbc << 32)"

     --#SUMMARY "Failed to get the address of the XBC Global Semaphore."
     --#ARGUMENTS {}
     --#SEVERITY WARNING
     --#TIMEINDEX 100
     --#STATE OPERATIONAL
::= 10529


hpevtFailWrtXbcGlobSemphrAfrRls TRAP-TYPE
     ENTERPRISE hpIpfE0Events
     VARIABLES { hpIpfEvtDetailStr }
     DESCRIPTION
        "Failed to write the XBC Global Semaphore.  Data Field: (cell num << 56) | (xbc << 32)"

     --#SUMMARY "Failed to write the XBC Global Semaphore."
     --#ARGUMENTS {}
     --#SEVERITY WARNING
     --#TIMEINDEX 100
     --#STATE OPERATIONAL
::= 10530


hpevtFailRelXbcGlobSemphr TRAP-TYPE
     ENTERPRISE hpIpfE0Events
     VARIABLES { hpIpfEvtDetailStr }
     DESCRIPTION
        "Failed to release the XBC Global Semaphore.  Data Field: (cell num << 56) | (xbc << 32)"

     --#SUMMARY "Failed to release the XBC Global Semaphore."
     --#ARGUMENTS {}
     --#SEVERITY WARNING
     --#TIMEINDEX 100
     --#STATE OPERATIONAL
::= 10532


hpevtFabPhsExeInvlOrdr TRAP-TYPE
     ENTERPRISE hpIpfE0Events
     VARIABLES { hpIpfEvtDetailStr }
     DESCRIPTION
        "Fabric phases have been executed in an invalid order"

     --#SUMMARY "Fabric phases have been executed in an invalid order."
     --#ARGUMENTS {}
     --#SEVERITY WARNING
     --#TIMEINDEX 100
     --#STATE OPERATIONAL
::= 10534


hpevtFabPhsExeInvlOrdrDatExpctPhs TRAP-TYPE
     ENTERPRISE hpIpfE0Events
     VARIABLES { hpIpfEvtDetailStr }
     DESCRIPTION
        "Fabric phases have been executed in an invalid order.  Data field indicates the expected phase."

     --#SUMMARY "Fabric phases have been executed in an invalid order.  Data field indicates the expected phase."
     --#ARGUMENTS {}
     --#SEVERITY WARNING
     --#TIMEINDEX 100
     --#STATE OPERATIONAL
::= 10535


hpevtFailGetAddrXbcToXbcLnk TRAP-TYPE
     ENTERPRISE hpIpfE0Events
     VARIABLES { hpIpfEvtDetailStr }
     DESCRIPTION
        "Failed to get an address when opening XBC to XBC links.  Data field is return value from GetAlbAddrBlk function.  Internal debug only."

     --#SUMMARY "Failed to get an address when opening XBC to XBC links."
     --#ARGUMENTS {}
     --#SEVERITY WARNING
     --#TIMEINDEX 100
     --#STATE OPERATIONAL
::= 10558


hpevtFailOpnFabLnk TRAP-TYPE
     ENTERPRISE hpIpfE0Events
     VARIABLES { hpIpfEvtDetailStr }
     DESCRIPTION
        "Failed to open a fabric link.
Data field: [31:0] - error status from OpenFabricLink
                 [39:32] - XBC ID
                 [51:44] - XBC port number"

     --#SUMMARY "Failed to open a fabric link."
     --#ARGUMENTS {}
     --#SEVERITY WARNING
     --#TIMEINDEX 100
     --#STATE OPERATIONAL
::= 10559


hpevtErrWrtXbcRetRout TRAP-TYPE
     ENTERPRISE hpIpfE0Events
     VARIABLES { hpIpfEvtDetailStr }
     DESCRIPTION
        "Error when writing the XBC return route.
Data field: [31:0] - error status from WriteRouteReg
                 [39:32] - XBC ID
                 [51:44] - XBC port number"

     --#SUMMARY "Error when writing the XBC return route."
     --#ARGUMENTS {}
     --#SEVERITY WARNING
     --#TIMEINDEX 100
     --#STATE OPERATIONAL
::= 10560


hpevtErrEnblXbcRetRout TRAP-TYPE
     ENTERPRISE hpIpfE0Events
     VARIABLES { hpIpfEvtDetailStr }
     DESCRIPTION
        "Error enabling the XBC return route.
Data field: [31:0] - error status from WriteRouteEnable
                 [39:32] - XBC ID
                 [51:44] - XBC port number"

     --#SUMMARY "Error enabling the XBC return route"
     --#ARGUMENTS {}
     --#SEVERITY WARNING
     --#TIMEINDEX 100
     --#STATE OPERATIONAL
::= 10561


hpevtFailDisprsRoutAcrssLnk TRAP-TYPE
     ENTERPRISE hpIpfE0Events
     VARIABLES { hpIpfEvtDetailStr }
     DESCRIPTION
        "failed to disperse the routes across links.
Data field: [31:0] - error status from GetDispersedOutboundPort
                 [39:32] - XBC ID
                 [51:44] - XBC port number"

     --#SUMMARY "Failed to disperse the routes across links."
     --#ARGUMENTS {}
     --#SEVERITY WARNING
     --#TIMEINDEX 100
     --#STATE OPERATIONAL
::= 10564


hpevtErrSetXbcToXbcLnkRoutX TRAP-TYPE
     ENTERPRISE hpIpfE0Events
     VARIABLES { hpIpfEvtDetailStr }
     DESCRIPTION
        "Error setting up XBC-XBC link for routing across it.
Data field: [31:0] - error status from SetupXbcToXbcLinks
                 [39:32] - XBC ID
                 [51:44] - XBC port number
"

     --#SUMMARY "Error setting up XBC-XBC link for routing across it."
     --#ARGUMENTS {}
     --#SEVERITY WARNING
     --#TIMEINDEX 100
     --#STATE OPERATIONAL
::= 10565


hpevtErrRoutRemtside TRAP-TYPE
     ENTERPRISE hpIpfE0Events
     VARIABLES { hpIpfEvtDetailStr }
     DESCRIPTION
        "Error while routing the remote side of a route.
Data field: [31:0] - error status from RouteRemoteXbcPort
                 [39:32] - XBC ID
                 [51:44] - XBC port number
                 [59:52] - Destination cell number:"

     --#SUMMARY "Error while routing the remote side of a route."
     --#ARGUMENTS {}
     --#SEVERITY WARNING
     --#TIMEINDEX 100
     --#STATE OPERATIONAL
::= 10566


hpevtErrGetAddrRoutRemtXbc TRAP-TYPE
     ENTERPRISE hpIpfE0Events
     VARIABLES { hpIpfEvtDetailStr }
     DESCRIPTION
        "Error getting address while routing the remote XBC.
Data field: [31:0] - error status from GetAlbAddrBlk
                 [39:32] - XBC ID
                 [51:44] - XBC port number"

     --#SUMMARY "Error getting address while routing the remote XBC."
     --#ARGUMENTS {}
     --#SEVERITY WARNING
     --#TIMEINDEX 100
     --#STATE OPERATIONAL
::= 10567


hpevtErrGetNgbrInfo TRAP-TYPE
     ENTERPRISE hpIpfE0Events
     VARIABLES { hpIpfEvtDetailStr }
     DESCRIPTION
        "Error geting the neighbor info.
Data field: [31:0] - error status from AlbGetNeighborInfo
                 [39:32] - XBC ID
                 [51:44] - XBC port number"

     --#SUMMARY "Error geting the neighbor info."
     --#ARGUMENTS {}
     --#SEVERITY WARNING
     --#TIMEINDEX 100
     --#STATE OPERATIONAL
::= 10568


hpevtErrFindShrtRout TRAP-TYPE
     ENTERPRISE hpIpfE0Events
     VARIABLES { hpIpfEvtDetailStr }
     DESCRIPTION
        "Error finding the shortest route.  Most likely a firmware error or data corruption.
Data field: [31:0] - error status from VM_FindShortestRoute
                 [39:32] - Destination XBC ID
                 [59:52] - Destination Cell number"

     --#SUMMARY "Error finding the shortest route"
     --#ARGUMENTS {}
     --#SEVERITY WARNING
     --#TIMEINDEX 100
     --#STATE OPERATIONAL
::= 10569


hpevtErrWrtRemtXbcRoutReg TRAP-TYPE
     ENTERPRISE hpIpfE0Events
     VARIABLES { hpIpfEvtDetailStr }
     DESCRIPTION
        "error writing the remote XBC routing register.
Data field: [31:0] - error status from WriteRouteReg
                 [39:32] - XBC ID
                 [51:44] - XBC port number
                 [59:52] - Destination cell number"

     --#SUMMARY "Error writing the remote XBC routing register."
     --#ARGUMENTS {}
     --#SEVERITY WARNING
     --#TIMEINDEX 100
     --#STATE OPERATIONAL
::= 10570


hpevtErrEnblRoutRemtXbc TRAP-TYPE
     ENTERPRISE hpIpfE0Events
     VARIABLES { hpIpfEvtDetailStr }
     DESCRIPTION
        "error enabling the routes on the remote XBC.
Data field: [31:0] - error status from WriteRouteEnable
                 [39:32] - XBC ID
                 [51:44] - XBC port number
                 [59:52] - Destination cell number"

     --#SUMMARY "Error enabling the routes on the remote XBC."
     --#ARGUMENTS {}
     --#SEVERITY WARNING
     --#TIMEINDEX 100
     --#STATE OPERATIONAL
::= 10571


hpevtErrWrtRoutRegLocXbc TRAP-TYPE
     ENTERPRISE hpIpfE0Events
     VARIABLES { hpIpfEvtDetailStr }
     DESCRIPTION
        "Error writing the routing register on the local XBC.
Data field: [31:0] - error status from WriteRouteReg
                 [39:32] - XBC ID
                 [51:44] - XBC port number"

     --#SUMMARY "Error writing the routing register on the local XBC."
     --#ARGUMENTS {}
     --#SEVERITY WARNING
     --#TIMEINDEX 100
     --#STATE OPERATIONAL
::= 10572


hpevtErrWrtLocXbcRoutRegRchRemtCel TRAP-TYPE
     ENTERPRISE hpIpfE0Events
     VARIABLES { hpIpfEvtDetailStr }
     DESCRIPTION
        "Error writing the local XBC routing registers to reach a remote cell.
Data field: [31:0] - error status from WriteRouteReg
                 [39:32] - XBC ID
                 [51:44] - XBC port number"

     --#SUMMARY "Error writing the local XBC routing registers to reach a remote cell."
     --#ARGUMENTS {}
     --#SEVERITY WARNING
     --#TIMEINDEX 100
     --#STATE OPERATIONAL
::= 10573


hpevtErrEnblLocXbcRout TRAP-TYPE
     ENTERPRISE hpIpfE0Events
     VARIABLES { hpIpfEvtDetailStr }
     DESCRIPTION
        "Error enabling the local XBC routes.
Data field: [31:0] - error status from WriteRouteEnable
                 [39:32] - XBC ID
                 [51:44] - XBC port number"

     --#SUMMARY "Error enabling the local XBC routes."
     --#ARGUMENTS {}
     --#SEVERITY WARNING
     --#TIMEINDEX 100
     --#STATE OPERATIONAL
::= 10574


hpevtSynGrphFailPhs4 TRAP-TYPE
     ENTERPRISE hpIpfE0Events
     VARIABLES { hpIpfEvtDetailStr }
     DESCRIPTION
        "SynchGraphs() failed during Arches Fabric Phase 4.
Data field: return value from SynchGraphs()"

     --#SUMMARY "SynchGraphs() failed during Arches Fabric Phase 4.  Data field: return value from SynchGraphs()."
     --#ARGUMENTS {}
     --#SEVERITY WARNING
     --#TIMEINDEX 100
     --#STATE OPERATIONAL
::= 10617


hpevtVmVertxFailSyncGrph TRAP-TYPE
     ENTERPRISE hpIpfE0Events
     VARIABLES { hpIpfEvtDetailStr }
     DESCRIPTION
        "VM_DeleteVertex() failed in SynchGraphs().
Data field: (vertex id << 32) | (vertex type << 56) | (return value from VM_DeleteVertex())"

     --#SUMMARY "VM_DeleteVertex() failed in SynchGraphs().  Data field: (vertex id  32) | (vertex type  56) | (return value from VM_DeleteVertex())."
     --#ARGUMENTS {}
     --#SEVERITY WARNING
     --#TIMEINDEX 100
     --#STATE OPERATIONAL
::= 10619


hpevtVmEdgFailFncSyncGrph TRAP-TYPE
     ENTERPRISE hpIpfE0Events
     VARIABLES { hpIpfEvtDetailStr }
     DESCRIPTION
        "VM_DeleteEdge() failed in the Arches Fabric function SynchGraphs().
Data field:(vertex id1 << 32) | (vertex port1 << 48) | (vertex type1 << 56) |
                (vertex id2 << 0)  | (vertex port2 << 16) | (vertex type2 << 24)"

     --#SUMMARY "VM_DeleteEdge() failed in the Arches Fabric function SynchGraphs().  Data field:(vertex id1  32) | (vertex port1  48) | (vertex type1  56) | (vertex id2  0)  | (vertex port2  16) | (vertex type2  24)."
     --#ARGUMENTS {}
     --#SEVERITY WARNING
     --#TIMEINDEX 100
     --#STATE OPERATIONAL
::= 10620


hpevtUnexpctErrCalVertxMod TRAP-TYPE
     ENTERPRISE hpIpfE0Events
     VARIABLES { hpIpfEvtDetailStr }
     DESCRIPTION
        "Unexpected error when calling an Arches Fabric vertex module function.
Data field: return value from vertex module function"

     --#SUMMARY "Unexpected error when calling an Arches Fabric vertex module function.  Data field: return value from vertex module function."
     --#ARGUMENTS {}
     --#SEVERITY WARNING
     --#TIMEINDEX 100
     --#STATE OPERATIONAL
::= 10621


hpevtUnexpctRetVertxModCopCelGrph TRAP-TYPE
     ENTERPRISE hpIpfE0Events
     VARIABLES { hpIpfEvtDetailStr }
     DESCRIPTION
        "Unexpected return from an Arches Fabric vertex module function while copying a cell's graph.  Data field: return value from vertex module function"

     --#SUMMARY "Unexpected return from an Arches Fabric vertex module function while copying a cell's graph.  Data field: return value from vertex module function."
     --#ARGUMENTS {}
     --#SEVERITY WARNING
     --#TIMEINDEX 100
     --#STATE OPERATIONAL
::= 10622


hpevtChecksumPdtFailed TRAP-TYPE
     ENTERPRISE hpIpfE0Events
     VARIABLES { hpIpfEvtDetailStr }
     DESCRIPTION
        "The checksum update for the PDT has failed."

     --#SUMMARY "The checksum update for the PDT has failed."
     --#ARGUMENTS {}
     --#SEVERITY WARNING
     --#TIMEINDEX 100
     --#STATE OPERATIONAL
::= 10623


hpevtChecksumNvmBad TRAP-TYPE
     ENTERPRISE hpIpfE0Events
     VARIABLES { hpIpfEvtDetailStr }
     DESCRIPTION
        "The checksum in the memory area of NVM is bad.  Memory NVM will be cleared."

     --#SUMMARY "The checksum in the memory area of NVM is bad."
     --#ARGUMENTS {}
     --#SEVERITY WARNING
     --#TIMEINDEX 100
     --#STATE OPERATIONAL
::= 10625


hpevtChecksumCalcFailed TRAP-TYPE
     ENTERPRISE hpIpfE0Events
     VARIABLES { hpIpfEvtDetailStr }
     DESCRIPTION
        "Checksum calculation failed."

     --#SUMMARY "Checksum calculation failed."
     --#ARGUMENTS {}
     --#SEVERITY WARNING
     --#TIMEINDEX 100
     --#STATE OPERATIONAL
::= 10626


hpevtSalandBmcTokenBad TRAP-TYPE
     ENTERPRISE hpIpfE0Events
     VARIABLES { hpIpfEvtDetailStr }
     DESCRIPTION
        "The BMC copy and SAL copy of the token specified in the data field has been initialized from the default value for the token due to an IPMI error and SAL NVM error."

     --#SUMMARY "Both SAL's copy and BMC copy of the token specified in the data field is bad."
     --#ARGUMENTS {}
     --#SEVERITY WARNING
     --#TIMEINDEX 100
     --#STATE OPERATIONAL
::= 10628


hpevtBkPlaneCable TRAP-TYPE
     ENTERPRISE hpIpfE0Events
     VARIABLES { hpIpfEvtDetailStr }
     DESCRIPTION
        "Detected incompatibility between the cell board and the I/O backplane and/or I/O backplane cables."

     --#SUMMARY "Incompatible I/O Backplane or I/O cables installed."
     --#ARGUMENTS {}
     --#SEVERITY CRITICAL
     --#TIMEINDEX 100
     --#STATE OPERATIONAL
::= 10629


hpevtFparUnusable TRAP-TYPE
     ENTERPRISE hpIpfE0Events
     VARIABLES { hpIpfEvtDetailStr }
     DESCRIPTION
        "The fPar identified by the event detail will be unusable. Other events may preceed this event which will help to diagnose the failure. A possible cause is that the system exhausted unused NVRAM."

     --#SUMMARY "The fPar identified by the event detail will be unusable."
     --#ARGUMENTS {}
     --#SEVERITY WARNING
     --#TIMEINDEX 100
     --#STATE OPERATIONAL
::= 10698


hpevtFWoutOfNvram TRAP-TYPE
     ENTERPRISE hpIpfE0Events
     VARIABLES { hpIpfEvtDetailStr }
     DESCRIPTION
        "Firmware is out of NVRAM and cannot built the ILM memory slice device map"

     --#SUMMARY "Firmware is out of NVRAM and cannot built the ILM memory slice device map"
     --#ARGUMENTS {}
     --#SEVERITY CRITICAL
     --#TIMEINDEX 100
     --#STATE OPERATIONAL
::= 10702


hpevtNvramCPUCorrupt TRAP-TYPE
     ENTERPRISE hpIpfE0Events
     VARIABLES { hpIpfEvtDetailStr }
     DESCRIPTION
        "The NVRAM for the CPU map is corrupt and cannot be trusted. It appears that there are more CPUs in the map than the size of the map can hold."

     --#SUMMARY "The NVRAM for the CPU map is corrupt and cannot be trusted. It appears that there are more CPUs in the map than the size of the map can hold."
     --#ARGUMENTS {}
     --#SEVERITY CRITICAL
     --#TIMEINDEX 100
     --#STATE OPERATIONAL
::= 10703


hpevtNvramIOCorrupt TRAP-TYPE
     ENTERPRISE hpIpfE0Events
     VARIABLES { hpIpfEvtDetailStr }
     DESCRIPTION
        "The NVRAM for the IO device ownership map is corrupt and cannot be trusted. It appears that there are more IO devices in the map than the size of the map can hold."

     --#SUMMARY "The NVRAM for the IO device ownership map is corrupt and cannot be trusted. It appears that there are more IO devices in the map than the size of the map can hold."
     --#ARGUMENTS {}
     --#SEVERITY CRITICAL
     --#TIMEINDEX 100
     --#STATE OPERATIONAL
::= 10704


hpevtNvramLocMemCorrupt TRAP-TYPE
     ENTERPRISE hpIpfE0Events
     VARIABLES { hpIpfEvtDetailStr }
     DESCRIPTION
        "The NVRAM for the cell local memory map is corrupt and cannot be trusted. It appears that there are more memory slices in the map than the size of the map can hold."

     --#SUMMARY "The NVRAM for the cell local memory map is corrupt and cannot be trusted. It appears that there are more memory slices in the map than the size of the map can hold."
     --#ARGUMENTS {}
     --#SEVERITY CRITICAL
     --#TIMEINDEX 100
     --#STATE OPERATIONAL
::= 10705


hpevtFWInconsistExist TRAP-TYPE
     ENTERPRISE hpIpfE0Events
     VARIABLES { hpIpfEvtDetailStr }
     DESCRIPTION
        "An internal firmware inconsistency exists or the server exhausted its internal resources and is unable to create an fPars EFI ownership variable for a CPU device in the partition. Either of these conditions is fatal."

     --#SUMMARY "An internal firmware inconsistency exists or the server exhausted its internal resources and is unable to create an fPars EFI ownership variable for a CPU device in the partition. Either of these conditions is fatal."
     --#ARGUMENTS {}
     --#SEVERITY CRITICAL
     --#TIMEINDEX 100
     --#STATE OPERATIONAL
::= 10706


hpevtFWUnableCreatefParsIO TRAP-TYPE
     ENTERPRISE hpIpfE0Events
     VARIABLES { hpIpfEvtDetailStr }
     DESCRIPTION
        "An internal firmware inconsistency exists or the server exhausted its internal resources and is unable to create an fPars EFI ownership variable for an IO device in the partition. Either of these conditions is fatal."

     --#SUMMARY "An internal firmware inconsistency exists or the server exhausted its internal resources and is unable to create an fPars EFI ownership variable for an IO device in the partition. Either of these conditions is fatal."
     --#ARGUMENTS {}
     --#SEVERITY CRITICAL
     --#TIMEINDEX 100
     --#STATE OPERATIONAL
::= 10707


hpevtFWUnableCreatefParsCLM TRAP-TYPE
     ENTERPRISE hpIpfE0Events
     VARIABLES { hpIpfEvtDetailStr }
     DESCRIPTION
        "An internal firmware inconsistency exists or the server exhausted its internal resources and is unable to create an fPars EFI ownership variable for a CLM device in the partition. Either of these conditions is fatal."

     --#SUMMARY "An internal firmware inconsistency exists or the server exhausted its internal resources and is unable to create an fPars EFI ownership variable for a CLM device in the partition. Either of these conditions is fatal."
     --#ARGUMENTS {}
     --#SEVERITY CRITICAL
     --#TIMEINDEX 100
     --#STATE OPERATIONAL
::= 10708


hpevtFWOutOfNvram TRAP-TYPE
     ENTERPRISE hpIpfE0Events
     VARIABLES { hpIpfEvtDetailStr }
     DESCRIPTION
        "Firmware has run out of NVRAM and cannot create the needed variable(s)"

     --#SUMMARY "Firmware has run out of NVRAM and cannot create the needed variable(s)"
     --#ARGUMENTS {}
     --#SEVERITY WARNING
     --#TIMEINDEX 100
     --#STATE OPERATIONAL
::= 10771


hpevtFWLbaReconfigFail TRAP-TYPE
     ENTERPRISE hpIpfE0Events
     VARIABLES { hpIpfEvtDetailStr }
     DESCRIPTION
        "The call to the IOC firmware component method 'LbaReconfig' failed, probably a low-level hardware error. The fPar BSP is identified in bits 63..32 of the event detail, the fPar owning this CPU and LBA is identified in bits 31..16 and the number of the Rope is identified in bits 15..0."

     --#SUMMARY "The call to the IOC firmware component method "LbaReconfig" failed, probably a low-level hardware error. The fPar BSP is identified in bits 63..32 of the event detail, the fPar owning this CPU and LBA is identified in bits 31..16."
     --#ARGUMENTS {}
     --#SEVERITY WARNING
     --#TIMEINDEX 100
     --#STATE OPERATIONAL
::= 10772


hpevtCpuModuleBadConfig TRAP-TYPE
     ENTERPRISE hpIpfE0Events
     VARIABLES { hpIpfEvtDetailStr }
     DESCRIPTION
        "The CPU modules have been installed in an illegal configuration on the cell board."

     --#SUMMARY "The CPU modules have been installed in an illegal configuration on the cell board"
     --#ARGUMENTS {}
     --#SEVERITY CRITICAL
     --#TIMEINDEX 100
     --#STATE OPERATIONAL
::= 10779


hpevtCpuInvalidTerminator TRAP-TYPE
     ENTERPRISE hpIpfE0Events
     VARIABLES { hpIpfEvtDetailStr }
     DESCRIPTION
        "An invalid CPU terminator card is installed on the cell board.  The data field indicates the physical location of the offending socket."

     --#SUMMARY "Invalid CPU terminator installed on the cell board."
     --#ARGUMENTS {}
     --#SEVERITY CRITICAL
     --#TIMEINDEX 100
     --#STATE OPERATIONAL
::= 10780


hpevtInvocationSoftResetCode TRAP-TYPE
     ENTERPRISE hpIpfE0Events
     VARIABLES { hpIpfEvtDetailStr }
     DESCRIPTION
        "Invocation of the soft reset code code from an interrupt or similar vector,
or improper locking/releasing of semaphores."

     --#SUMMARY "Invocation of the soft reset code code from an interrupt or similar vector,"
     --#ARGUMENTS {}
     --#SEVERITY CRITICAL
     --#TIMEINDEX 100
     --#STATE OPERATIONAL
::= 10793


hpevtDataSm4SelfReset TRAP-TYPE
     ENTERPRISE hpIpfE0Events
     VARIABLES { hpIpfEvtDetailStr }
     DESCRIPTION
        "Data field is count of cpus held by the sm4 which issues the event (and is trying to reset itself).  Indicates invocation of the SoftResetCpu code from an interrupt or similar vector where the processor was modifying critical resources, or improper locking/releasing of semaphores."

     --#SUMMARY "Data field is count of cpus held by the sm4 which issues the event (and is trying to reset itself).  Indicates invocation of the SoftResetCpu code from an interrupt or similar vector."
     --#ARGUMENTS {}
     --#SEVERITY CRITICAL
     --#TIMEINDEX 100
     --#STATE OPERATIONAL
::= 10794


hpevtfParsfailRelseResrce TRAP-TYPE
     ENTERPRISE hpIpfE0Events
     VARIABLES { hpIpfEvtDetailStr }
     DESCRIPTION
        "A reset of an fPar discovered that an fPar failed to release critical resources within a reasonable time."

     --#SUMMARY "A reset of an fPar discovered that an fPar failed to release critical resources within a reasonable time."
     --#ARGUMENTS {}
     --#SEVERITY CRITICAL
     --#TIMEINDEX 100
     --#STATE OPERATIONAL
::= 10795


hpevtPFMManyErrors TRAP-TYPE
     ENTERPRISE hpIpfE0Events
     VARIABLES { hpIpfEvtDetailStr }
     DESCRIPTION
        "Significant numbers of corrected memory errors have been detected on the memory subsystem"

     --#SUMMARY "Significant numbers of corrected memory errors have been detected on the memory subsystem"
     --#ARGUMENTS {}
     --#SEVERITY WARNING
     --#TIMEINDEX 100
     --#STATE OPERATIONAL
::= 10814


hpevtPFMOverTempProc TRAP-TYPE
     ENTERPRISE hpIpfE0Events
     VARIABLES { hpIpfEvtDetailStr }
     DESCRIPTION
        "Over-temperature condition detected on a processor"

     --#SUMMARY "Over-temperature condition detected on a processor"
     --#ARGUMENTS {}
     --#SEVERITY WARNING
     --#TIMEINDEX 100
     --#STATE OPERATIONAL
::= 10822


hpevtPFMCacheErrorProc TRAP-TYPE
     ENTERPRISE hpIpfE0Events
     VARIABLES { hpIpfEvtDetailStr }
     DESCRIPTION
        "Cache errors detected on a processor"

     --#SUMMARY "Cache errors detected on a processor"
     --#ARGUMENTS {}
     --#SEVERITY WARNING
     --#TIMEINDEX 100
     --#STATE OPERATIONAL
::= 10823


hpevtPFMCorrecErrorCache TRAP-TYPE
     ENTERPRISE hpIpfE0Events
     VARIABLES { hpIpfEvtDetailStr }
     DESCRIPTION
        "Corrected errors detected in the cache portion of the memory for a processor module"

     --#SUMMARY "Corrected errors detected in the cache portion of the memory for a processor module"
     --#ARGUMENTS {}
     --#SEVERITY WARNING
     --#TIMEINDEX 100
     --#STATE OPERATIONAL
::= 10824


hpevtPFMCorrErrSysBus TRAP-TYPE
     ENTERPRISE hpIpfE0Events
     VARIABLES { hpIpfEvtDetailStr }
     DESCRIPTION
        "Corrected errors detected on the system bus for a processor module"

     --#SUMMARY "Corrected errors detected on the system bus for a processor module"
     --#ARGUMENTS {}
     --#SEVERITY WARNING
     --#TIMEINDEX 100
     --#STATE OPERATIONAL
::= 10825


hpevtPFMCorrErrProcBus TRAP-TYPE
     ENTERPRISE hpIpfE0Events
     VARIABLES { hpIpfEvtDetailStr }
     DESCRIPTION
        "Corrected errors detected on the processor bus for a processor module"

     --#SUMMARY "Corrected errors detected on the processor bus for a processor module"
     --#ARGUMENTS {}
     --#SEVERITY WARNING
     --#TIMEINDEX 100
     --#STATE OPERATIONAL
::= 10826


hpevtPFMErrTagMemProc TRAP-TYPE
     ENTERPRISE hpIpfE0Events
     VARIABLES { hpIpfEvtDetailStr }
     DESCRIPTION
        "Corrected errors detected in the tag portion of the memory for a processor module"

     --#SUMMARY "Corrected errors detected in the tag portion of the memory for a processor module"
     --#ARGUMENTS {}
     --#SEVERITY WARNING
     --#TIMEINDEX 100
     --#STATE OPERATIONAL
::= 10827


hpevtfParsNotEnableBoot TRAP-TYPE
     ENTERPRISE hpIpfE0Events
     VARIABLES { hpIpfEvtDetailStr }
     DESCRIPTION
        "fPars-mode EFI variable is set to enable fPars operation but no fPars are actually enabled to boot. So the server boots in hard partition mode."

     --#SUMMARY "fPars-mode EFI variable is set to enable fPars operation but no fPars are actually enabled to boot. So the server boots in hard partition mode."
     --#ARGUMENTS {}
     --#SEVERITY WARNING
     --#TIMEINDEX 100
     --#STATE OPERATIONAL
::= 10830


hpevtfParsNotRecveOwnShip TRAP-TYPE
     ENTERPRISE hpIpfE0Events
     VARIABLES { hpIpfEvtDetailStr }
     DESCRIPTION
        "An fPar was directed to reset using the ESIT DirectedfParResetAndMigrate() service but the target (recipient) fPar of the resources is in a state that cannot receive ownership of these resources."

     --#SUMMARY "An fPar was directed to reset using the ESIT DirectedfParResetAndMigrate() service but the target (recipient) fPar of the resources is in a state that cannot receive ownership of these resources."
     --#ARGUMENTS {}
     --#SEVERITY WARNING
     --#TIMEINDEX 100
     --#STATE OPERATIONAL
::= 10832


hpevtFWErrSetNvramVal TRAP-TYPE
     ENTERPRISE hpIpfE0Events
     VARIABLES { hpIpfEvtDetailStr }
     DESCRIPTION
        "Firmware error setting the NVRAM value of preferred-bsp for the vPars monitor. The partition will boot using the PD monarch, but the value of preferred-bsp may not match this CPU."

     --#SUMMARY "Firmware error setting the NVRAM value of preferred-bsp for the vPars monitor. The partition will boot using the PD monarch, but the value of preferred-bsp may not match this CPU."
     --#ARGUMENTS {}
     --#SEVERITY WARNING
     --#TIMEINDEX 100
     --#STATE OPERATIONAL
::= 10833


hpevtUnablWrtXbcPrtRoutTblEnblMsk TRAP-TYPE
     ENTERPRISE hpIpfE0Events
     VARIABLES { hpIpfEvtDetailStr }
     DESCRIPTION
        "Unable to write to an XBC port ROUTE_TABLE_ENABLE_MASK CSR in Arches Fabric Phase3.
Data field: (XBC port << 48) | (XBC ID < 32) | (route)"

     --#SUMMARY "Unable to write to an XBC port ROUTE_TABLE_ENABLE_MASK CSR in Arches Fabric Phase3.  Data field: (XBC port  48) | (XBC ID  32) | (route)."
     --#ARGUMENTS {}
     --#SEVERITY WARNING
     --#TIMEINDEX 100
     --#STATE OPERATIONAL
::= 10842


hpevtProcessIntrptUnRecoverble TRAP-TYPE
     ENTERPRISE hpIpfE0Events
     VARIABLES { hpIpfEvtDetailStr }
     DESCRIPTION
        "An unrecoverable processor interrupt occured. IPF firmware owned the processor interrupt vector table (IVT) at the time of the interrupt."

     --#SUMMARY "An unrecoverable processor interrupt occured. IPF firmware owned the processor interrupt vector table (IVT) at the time of the interrupt."
     --#ARGUMENTS {}
     --#SEVERITY CRITICAL
     --#TIMEINDEX 100
     --#STATE OPERATIONAL
::= 10853


hpevtSBASetDevMaskFail TRAP-TYPE
     ENTERPRISE hpIpfE0Events
     VARIABLES { hpIpfEvtDetailStr }
     DESCRIPTION
        "SBA call to LBA SetDeviceMask method fails."

     --#SUMMARY "SBA call to LBA SetDeviceMask method fails."
     --#ARGUMENTS {}
     --#SEVERITY CRITICAL
     --#TIMEINDEX 100
     --#STATE OPERATIONAL
::= 10871


hpevtLBASlotDevScanErr TRAP-TYPE
     ENTERPRISE hpIpfE0Events
     VARIABLES { hpIpfEvtDetailStr }
     DESCRIPTION
        "LBA slot device scan error"

     --#SUMMARY "LBA slot device scan error."
     --#ARGUMENTS {}
     --#SEVERITY CRITICAL
     --#TIMEINDEX 100
     --#STATE OPERATIONAL
::= 10927


hpevtInadequateMemTofPar TRAP-TYPE
     ENTERPRISE hpIpfE0Events
     VARIABLES { hpIpfEvtDetailStr }
     DESCRIPTION
        "There is none (or inadequate) memory slice resoruce assigned to the fPar so it cannot boot its instance. The fPar will be disabled (enter a spinloop) because it cannot boot, or if in vPars mode will return control to the monitor."

     --#SUMMARY "There is none (or inadequate) memory slice resoruce assigned to the fPar so it cannot boot its instance. The fPar will be disabled (enter a spinloop) because it cannot boot, or if in vPars mode will return control to the monitor."
     --#ARGUMENTS {}
     --#SEVERITY WARNING
     --#TIMEINDEX 100
     --#STATE OPERATIONAL
::= 10936


hpevtFailCollVertxInfo TRAP-TYPE
     ENTERPRISE hpIpfE0Events
     VARIABLES { hpIpfEvtDetailStr }
     DESCRIPTION
        "Couldn't collect vertex information during Fabric Info call.  Data Field: return status"

     --#SUMMARY "Couldn't collect vertex information during Fabric Info call.  Data Field: return status."
     --#ARGUMENTS {}
     --#SEVERITY WARNING
     --#TIMEINDEX 100
     --#STATE OPERATIONAL
::= 10937


hpevtFailCollVertxFabInfoCall TRAP-TYPE
     ENTERPRISE hpIpfE0Events
     VARIABLES { hpIpfEvtDetailStr }
     DESCRIPTION
        "Couldn't collect the vertices during the Fabric Info call.  Data Field: number of vertices returned"

     --#SUMMARY "Couldn't collect the vertices during the Fabric Info call.  Data Field: number of vertices returned."
     --#ARGUMENTS {}
     --#SEVERITY WARNING
     --#TIMEINDEX 100
     --#STATE OPERATIONAL
::= 10938


hpevtFailFndEdgeProcCall TRAP-TYPE
     ENTERPRISE hpIpfE0Events
     VARIABLES { hpIpfEvtDetailStr }
     DESCRIPTION
        "Couldn't find all the edges during a procedure call.  Data Field: return status"

     --#SUMMARY "Couldn't find all the edges during a procedure call.  Data Field: return status."
     --#ARGUMENTS {}
     --#SEVERITY WARNING
     --#TIMEINDEX 100
     --#STATE OPERATIONAL
::= 10939


hpevtFailFndEdgProcCall TRAP-TYPE
     ENTERPRISE hpIpfE0Events
     VARIABLES { hpIpfEvtDetailStr }
     DESCRIPTION
        "Couldn't find an appropriate number of edges during a procedure call.  Data Field: the number of edges found"

     --#SUMMARY "Couldn't find an appropriate number of edges during a procedure call.  Data Field: the number of edges found."
     --#ARGUMENTS {}
     --#SEVERITY WARNING
     --#TIMEINDEX 100
     --#STATE OPERATIONAL
::= 10940


hpevtManyEdgEncntProcCall TRAP-TYPE
     ENTERPRISE hpIpfE0Events
     VARIABLES { hpIpfEvtDetailStr }
     DESCRIPTION
        "Too many edges were encountered during a procedure call.  Data Field: link count"

     --#SUMMARY "Too many edges were encountered during a procedure call.  Data Field: link count."
     --#ARGUMENTS {}
     --#SEVERITY WARNING
     --#TIMEINDEX 100
     --#STATE OPERATIONAL
::= 10941


hpevtFailGetAddrProcCall TRAP-TYPE
     ENTERPRISE hpIpfE0Events
     VARIABLES { hpIpfEvtDetailStr }
     DESCRIPTION
        "Failed to get an address during a procedure call.  Data Field: return status"

     --#SUMMARY "Failed to get an address during a procedure call.  Data Field: return status."
     --#ARGUMENTS {}
     --#SEVERITY WARNING
     --#TIMEINDEX 100
     --#STATE OPERATIONAL
::= 10943


hpevtUnexpctStatEncntProcCall TRAP-TYPE
     ENTERPRISE hpIpfE0Events
     VARIABLES { hpIpfEvtDetailStr }
     DESCRIPTION
        "An unexpected state was encountered during a procedure call.  Data Field: state returned"

     --#SUMMARY "An unexpected state was encountered during a procedure call.  Data Field: state returned."
     --#ARGUMENTS {}
     --#SEVERITY WARNING
     --#TIMEINDEX 100
     --#STATE OPERATIONAL
::= 10944


hpevtUnablGetLnkHlthStatProcCall TRAP-TYPE
     ENTERPRISE hpIpfE0Events
     VARIABLES { hpIpfEvtDetailStr }
     DESCRIPTION
        "Unable to get the link health state during a procedure call.  Data Field: (cell num << 56) | (port << 44) | (xbc << 32)"

     --#SUMMARY "Unable to get the link health state during a procedure call.  Data Field: return status."
     --#ARGUMENTS {}
     --#SEVERITY WARNING
     --#TIMEINDEX 100
     --#STATE OPERATIONAL
::= 10945


hpevtFabDatFailCrcChk TRAP-TYPE
     ENTERPRISE hpIpfE0Events
     VARIABLES { hpIpfEvtDetailStr }
     DESCRIPTION
        "The fabric data failed a CRC check.  Data Field: (xbc port << 44 ) | (xbc << 32) | return status)"

     --#SUMMARY "The fabric data failed a CRC check.  Data Field: (xbc port  44 ) | (xbc  32) | return status)."
     --#ARGUMENTS {}
     --#SEVERITY WARNING
     --#TIMEINDEX 100
     --#STATE OPERATIONAL
::= 10946


hpevtVmCollVertcFailUnexpct TRAP-TYPE
     ENTERPRISE hpIpfE0Events
     VARIABLES { hpIpfEvtDetailStr }
     DESCRIPTION
        "VM_CollectVertices failed unexpectedly.  Could possibly be a data corruption problem.  Data field: (cell number << 56) | (return value from VM_CollectVertices)"

     --#SUMMARY "VM_CollectVertices failed unexpectedly.  Could possibly be a data corruption problem.  Data field: (cell number  56) | (return value from VM_CollectVertices)."
     --#ARGUMENTS {}
     --#SEVERITY WARNING
     --#TIMEINDEX 100
     --#STATE OPERATIONAL
::= 11032


hpevtUnablGenAlbArfSetCsr TRAP-TYPE
     ENTERPRISE hpIpfE0Events
     VARIABLES { hpIpfEvtDetailStr }
     DESCRIPTION
        "Unable to generate an ALB address in Arches Fabric ArfSetDefaultCSRs() function.
Data field:(cell number << 56) | (port number << 48) | (xbc ID < 32) | (return value)"

     --#SUMMARY "Unable to generate an ALB address in Arches Fabric ArfSetDefaultCSRs() function.  Data field:(cell number  56) | (port number  48) | (xbc ID  32) | (return value)."
     --#ARGUMENTS {}
     --#SEVERITY WARNING
     --#TIMEINDEX 100
     --#STATE OPERATIONAL
::= 11033


hpevtSetDefCsrFailUnexpct TRAP-TYPE
     ENTERPRISE hpIpfE0Events
     VARIABLES { hpIpfEvtDetailStr }
     DESCRIPTION
        "SetDefaultCSRs function failed unexpectedly.  Arches Fabric was unable to set XBC CSRs to default values.
Data field: return value from SetDefaultCSRs"

     --#SUMMARY "SetDefaultCSRs function failed unexpectedly.  Arches Fabric was unable to set XBC CSRs to default values.  Data field: return value from SetDefaultCSRs."
     --#ARGUMENTS {}
     --#SEVERITY WARNING
     --#TIMEINDEX 100
     --#STATE OPERATIONAL
::= 11034


hpevtEncntErrRout TRAP-TYPE
     ENTERPRISE hpIpfE0Events
     VARIABLES { hpIpfEvtDetailStr }
     DESCRIPTION
        "A problem was encountered while routing which prevented an appropriate route from being chosen.  Data Field: Destination Cell << 56 | XBC Port << 44 | XBC # << 32 | return status"

     --#SUMMARY "A problem was encountered while routing which prevented an appropriate route from being chosen.  Data Field: Destination Cell  56 | XBC Port  44 | XBC #  32 | return status."
     --#ARGUMENTS {}
     --#SEVERITY WARNING
     --#TIMEINDEX 100
     --#STATE OPERATIONAL
::= 11038


hpevtEncntErrRoutFab TRAP-TYPE
     ENTERPRISE hpIpfE0Events
     VARIABLES { hpIpfEvtDetailStr }
     DESCRIPTION
        "An error was encountered while routing the fabric.  This error prevents an appropriate route from being selected.  Data Field: Destination Cell << 56 | XBC Port << 44 | XBC # << 32 | return status"

     --#SUMMARY "An error was encountered while routing the fabric.  This error prevents an appropriate route from being selected.  Data Field: Destination Cell  56 | XBC Port  44 | XBC #  32 | return status."
     --#ARGUMENTS {}
     --#SEVERITY WARNING
     --#TIMEINDEX 100
     --#STATE OPERATIONAL
::= 11039


hpevtErrEncntRoutFabPrvntRoutSel TRAP-TYPE
     ENTERPRISE hpIpfE0Events
     VARIABLES { hpIpfEvtDetailStr }
     DESCRIPTION
        "An error was encountered while routing the fabric.  This error prevents an appropriate route from being selected.  Data Field: Destination Cell << 56 | XBC Port << 44 | XBC # << 32 | return status"

     --#SUMMARY "An error was encountered while routing the fabric.  This error prevents an appropriate route from being selected.  Data Field: Destination Cell  56 | XBC Port  44 | XBC #  32 | return status."
     --#ARGUMENTS {}
     --#SEVERITY WARNING
     --#TIMEINDEX 100
     --#STATE OPERATIONAL
::= 11040


hpevtErrEncntRoutFabPrvntRoutSelSw TRAP-TYPE
     ENTERPRISE hpIpfE0Events
     VARIABLES { hpIpfEvtDetailStr }
     DESCRIPTION
        "An error was encountered while routing the fabric.  This error prevents an appropriate route from being selected.  Data Field: Destination Cell << 56 | XBC Port << 44 | XBC # << 32 | switch fabric"

     --#SUMMARY "An error was encountered while routing the fabric.  This error prevents an appropriate route from being selected.  Data Field: Destination Cell  56 | XBC Port  44 | XBC #  32 | switch fabric"
     --#ARGUMENTS {}
     --#SEVERITY WARNING
     --#TIMEINDEX 100
     --#STATE OPERATIONAL
::= 11042


hpevtSysBckPlnPwr1p2LDOFault TRAP-TYPE
     ENTERPRISE hpIpfE0Events
     VARIABLES { hpIpfEvtDetailStr }
     DESCRIPTION
        "System backplane power has reported a 1.2v LDO fault. The data field contains the physical location of the fault."

     --#SUMMARY "System backplane power has reported a 1.2v LDO fault. The data field contains the physical location of the fault."
     --#ARGUMENTS {}
     --#SEVERITY CRITICAL
     --#TIMEINDEX 100
     --#STATE OPERATIONAL
::= 11452


hpevtSysBckPlnPwr2p5LDOFault TRAP-TYPE
     ENTERPRISE hpIpfE0Events
     VARIABLES { hpIpfEvtDetailStr }
     DESCRIPTION
        "System backplane power has reported a 2.5v LDO fault. The data field contains the physical location of the fault."

     --#SUMMARY "System backplane power has reported a 2.5v LDO fault. The data field contains the physical location of the fault."
     --#ARGUMENTS {}
     --#SEVERITY CRITICAL
     --#TIMEINDEX 100
     --#STATE OPERATIONAL
::= 11454


hpevtSysBckPlnPwr3p3HseFault TRAP-TYPE
     ENTERPRISE hpIpfE0Events
     VARIABLES { hpIpfEvtDetailStr }
     DESCRIPTION
        "System backplane power has reported a 3.3v house keeping power fault. The data field contains the physical location of the fault."

     --#SUMMARY "System backplane power has reported a 3.3v house keeping power fault. The data field contains the physical location of the fault."
     --#ARGUMENTS {}
     --#SEVERITY CRITICAL
     --#TIMEINDEX 100
     --#STATE OPERATIONAL
::= 11456


hpevtSysBckPlnPwr12Fault TRAP-TYPE
     ENTERPRISE hpIpfE0Events
     VARIABLES { hpIpfEvtDetailStr }
     DESCRIPTION
        "System backplane power has reported a 12v power fault. The data field contains the physical location of the fault."

     --#SUMMARY "System backplane power has reported a 12v power fault. The data field contains the physical location of the fault."
     --#ARGUMENTS {}
     --#SEVERITY CRITICAL
     --#TIMEINDEX 100
     --#STATE OPERATIONAL
::= 11459


hpevtSysBckPlnPwr3p3Fault TRAP-TYPE
     ENTERPRISE hpIpfE0Events
     VARIABLES { hpIpfEvtDetailStr }
     DESCRIPTION
        "System backplane power has reported a 3.3v power fault. The data field contains the physical location of the fault."

     --#SUMMARY "System backplane power has reported a 3.3v power fault. The data field contains the physical location of the fault."
     --#ARGUMENTS {}
     --#SEVERITY CRITICAL
     --#TIMEINDEX 100
     --#STATE OPERATIONAL
::= 11461


hpevtSysBckPlnPwr1p5Fault TRAP-TYPE
     ENTERPRISE hpIpfE0Events
     VARIABLES { hpIpfEvtDetailStr }
     DESCRIPTION
        "System backplane power has reported a 1.5v power fault. The data field contains the physical location of the fault."

     --#SUMMARY "System backplane power has reported a 1.5v power fault. The data field contains the physical location of the fault."
     --#ARGUMENTS {}
     --#SEVERITY CRITICAL
     --#TIMEINDEX 100
     --#STATE OPERATIONAL
::= 11463


hpevtSysBckPlnPwr2p5Fault TRAP-TYPE
     ENTERPRISE hpIpfE0Events
     VARIABLES { hpIpfEvtDetailStr }
     DESCRIPTION
        "System backplane power has reported a 2.5v power fault. The data field contains the physical location of the fault."

     --#SUMMARY "System backplane power has reported a 2.5v power fault. The data field contains the physical location of the fault."
     --#ARGUMENTS {}
     --#SEVERITY CRITICAL
     --#TIMEINDEX 100
     --#STATE OPERATIONAL
::= 11465


hpevtPwrRailPrvInsuffPwrToBckPln TRAP-TYPE
     ENTERPRISE hpIpfE0Events
     VARIABLES { hpIpfEvtDetailStr }
     DESCRIPTION
        "One or more power rails is providing insufficient power to the backplane."

     --#SUMMARY "One or more power rails is providing insufficient power to the backplane."
     --#ARGUMENTS {}
     --#SEVERITY CRITICAL
     --#TIMEINDEX 100
     --#STATE OPERATIONAL
::= 11467


hpevtRcsNoProvClkBckPln TRAP-TYPE
     ENTERPRISE hpIpfE0Events
     VARIABLES { hpIpfEvtDetailStr }
     DESCRIPTION
        "Clock fault for clocks supplied from the Redundant Clock Source (RCS) board to the system backplane.  RCS board is no longer providing clocks to the backplane. The data field contains the physical location of the RCS."

     --#SUMMARY "Clock fault for clocks supplied from the Redundant Clock Source (RCS) board to the system backplane.  RCS board is no longer providing clocks to the backplane. The data field contains the physical location of the RCS."
     --#ARGUMENTS {}
     --#SEVERITY CRITICAL
     --#TIMEINDEX 100
     --#STATE OPERATIONAL
::= 11468


hpevtHsoFaultOrRemv TRAP-TYPE
     ENTERPRISE hpIpfE0Events
     VARIABLES { hpIpfEvtDetailStr }
     DESCRIPTION
        "Clock fault for clocks supplied from the Hot Swap Oscillator (HSO) board to the system backplane.  HSO has reported a fault or has been removed. The data field contains the physical location of the HSO."

     --#SUMMARY "Clock fault for clocks supplied from the Hot Swap Oscillator (HSO) board to the system backplane.  HSO has reported a fault or has been removed. The data field contains the physical location of the HSO."
     --#ARGUMENTS {}
     --#SEVERITY CRITICAL
     --#TIMEINDEX 100
     --#STATE OPERATIONAL
::= 11471


hpevtOpClkNoMtchRcsHso TRAP-TYPE
     ENTERPRISE hpIpfE0Events
     VARIABLES { hpIpfEvtDetailStr }
     DESCRIPTION
        "The operational clock frequencies do not match between the Redundant Clock Source (RCS) and the Hot Swap Oscillator (HSO).  The data field contains the physical location of the HSO."

     --#SUMMARY "The operational clock frequencies do not match between the Redundant Clock Source (RCS) and the Hot Swap Oscillator (HSO).  The data field contains the physical location of the HSO."
     --#ARGUMENTS {}
     --#SEVERITY WARNING
     --#TIMEINDEX 100
     --#STATE OPERATIONAL
::= 11478


hpevtClkMrgnBckPlnFail TRAP-TYPE
     ENTERPRISE hpIpfE0Events
     VARIABLES { hpIpfEvtDetailStr }
     DESCRIPTION
        "The clock margin of the system backplane failed."

     --#SUMMARY "The clock margin of the system backplane failed."
     --#ARGUMENTS {}
     --#SEVERITY CRITICAL
     --#TIMEINDEX 100
     --#STATE OPERATIONAL
::= 11479


hpevtHsoNoRedund TRAP-TYPE
     ENTERPRISE hpIpfE0Events
     VARIABLES { hpIpfEvtDetailStr }
     DESCRIPTION
        "System backplane Hot Swap Oscillator (HSO) boards are NOT redundant."

     --#SUMMARY "System backplane Hot Swap Oscillator (HSO) boards are NOT redundant."
     --#ARGUMENTS {}
     --#SEVERITY WARNING
     --#TIMEINDEX 100
     --#STATE OPERATIONAL
::= 11481


hpevtHsoInsuff TRAP-TYPE
     ENTERPRISE hpIpfE0Events
     VARIABLES { hpIpfEvtDetailStr }
     DESCRIPTION
        "System backplane Hot Swap Oscillator (HSO) boards are insufficient."

     --#SUMMARY "System backplane Hot Swap Oscillator (HSO) boards are insufficient."
     --#ARGUMENTS {}
     --#SEVERITY CRITICAL
     --#TIMEINDEX 100
     --#STATE OPERATIONAL
::= 11482


hpevtFailRdRcsHso TRAP-TYPE
     ENTERPRISE hpIpfE0Events
     VARIABLES { hpIpfEvtDetailStr }
     DESCRIPTION
        "Failure reading Redundant Clock Source (RCS) or Hot Swap Oscillator HSO boards EEPROM.  Data field contains the physical location of the device."

     --#SUMMARY "Failure reading Redundant Clock Source (RCS) or Hot Swap Oscillator HSO boards EEPROM."
     --#ARGUMENTS {}
     --#SEVERITY WARNING
     --#TIMEINDEX 100
     --#STATE OPERATIONAL
::= 11483


hpevtFailWrtRcsHso TRAP-TYPE
     ENTERPRISE hpIpfE0Events
     VARIABLES { hpIpfEvtDetailStr }
     DESCRIPTION
        "Failure writing Redundant Clock Source (RCS) or Hot Swap Oscillator HSO boards EEPROM.  Data field contains the physical location of the device"

     --#SUMMARY "Failure writing Redundant Clock Source (RCS) or Hot Swap Oscillator HSO boards EEPROM."
     --#ARGUMENTS {}
     --#SEVERITY CRITICAL
     --#TIMEINDEX 100
     --#STATE OPERATIONAL
::= 11484


hpevtFailRdRpm TRAP-TYPE
     ENTERPRISE hpIpfE0Events
     VARIABLES { hpIpfEvtDetailStr }
     DESCRIPTION
        "Failure reading the Reset and Power Monitors (RPM) EEPROM.  Data field contains the physical location of the device."

     --#SUMMARY "Failure reading the Reset and Power Monitors (RPM) EEPROM."
     --#ARGUMENTS {}
     --#SEVERITY CRITICAL
     --#TIMEINDEX 100
     --#STATE OPERATIONAL
::= 11485


hpevtFailWrtRpm TRAP-TYPE
     ENTERPRISE hpIpfE0Events
     VARIABLES { hpIpfEvtDetailStr }
     DESCRIPTION
        "Failure writing the Reset and Power Monitors (RPM) EEPROM.  Datafield contains the physical location of the device"

     --#SUMMARY "Failure writing the Reset and Power Monitors (RPM) EEPROM."
     --#ARGUMENTS {}
     --#SEVERITY CRITICAL
     --#TIMEINDEX 100
     --#STATE OPERATIONAL
::= 11486


hpevtFailRdOsp TRAP-TYPE
     ENTERPRISE hpIpfE0Events
     VARIABLES { hpIpfEvtDetailStr }
     DESCRIPTION
        "Failure reading the Onboard System Programmers (OSP) EEPROM.  Datafield contains the physical location of the device"

     --#SUMMARY "Failure reading the Onboard System Programmers (OSP) EEPROM."
     --#ARGUMENTS {}
     --#SEVERITY CRITICAL
     --#TIMEINDEX 100
     --#STATE OPERATIONAL
::= 11487


hpevtFailWrtOsp TRAP-TYPE
     ENTERPRISE hpIpfE0Events
     VARIABLES { hpIpfEvtDetailStr }
     DESCRIPTION
        "Failure writing the Onboard System Programmers (OSP) EEPROM.  Datafield contains physical location of the device"

     --#SUMMARY "Failure writing the Onboard System Programmers (OSP) EEPROM."
     --#ARGUMENTS {}
     --#SEVERITY CRITICAL
     --#TIMEINDEX 100
     --#STATE OPERATIONAL
::= 11488


hpevtSbsFaultStrt TRAP-TYPE
     ENTERPRISE hpIpfE0Events
     VARIABLES { hpIpfEvtDetailStr }
     DESCRIPTION
        "Serial Bit Stream (SBS) fault on startup.  An SBS fault results in the MOAB's not being configured correctly."

     --#SUMMARY "SBS fault on startup."
     --#ARGUMENTS {}
     --#SEVERITY CRITICAL
     --#TIMEINDEX 100
     --#STATE OPERATIONAL
::= 11489


hpevtFailRdIObckPlnLpm TRAP-TYPE
     ENTERPRISE hpIpfE0Events
     VARIABLES { hpIpfEvtDetailStr }
     DESCRIPTION
        "Failure reading IO backplane LPM.  Datafield contains the physical location of the device."

     --#SUMMARY "Failure reading IO backplane LPM."
     --#ARGUMENTS {}
     --#SEVERITY WARNING
     --#TIMEINDEX 100
     --#STATE OPERATIONAL
::= 11495


hpevtFailWrtIOBckPlnLpm TRAP-TYPE
     ENTERPRISE hpIpfE0Events
     VARIABLES { hpIpfEvtDetailStr }
     DESCRIPTION
        "Failure writing IO backplane LPM.  Datafield contains physical location of device."

     --#SUMMARY "Failure writing IO backplane LPM."
     --#ARGUMENTS {}
     --#SEVERITY WARNING
     --#TIMEINDEX 100
     --#STATE OPERATIONAL
::= 11496


hpevtSysSoftViolateWellBhaveRule TRAP-TYPE
     ENTERPRISE hpIpfE0Events
     VARIABLES { hpIpfEvtDetailStr }
     DESCRIPTION
        "The system software violated one of the 'well-behavedness' rules of soft partitions and tried to call a firmware procedure within the firmware instance of a sibling. This is an access violation and firmware rejects the call"

     --#SUMMARY "The system software violated one of the 'well-behavedness' rules of soft partitions and tried to call a firmware procedure within the firmware instance of a sibling. This is an access violation and firmware rejects the call."
     --#ARGUMENTS {}
     --#SEVERITY WARNING
     --#TIMEINDEX 100
     --#STATE OPERATIONAL
::= 11515


hpevtAlbInitPrepUnablRdAlrecConfig TRAP-TYPE
     ENTERPRISE hpIpfE0Events
     VARIABLES { hpIpfEvtDetailStr }
     DESCRIPTION
        "AlbInitPrep was unable to read the ALREC_CONFIG CSR to determine whether the link is up or not.
Data field: unused"

     --#SUMMARY "AlbInitPrep was unable to read the ALREC_CONFIG CSR to determine whether the link is up or not.  Data field: unused"
     --#ARGUMENTS {}
     --#SEVERITY WARNING
     --#TIMEINDEX 100
     --#STATE OPERATIONAL
::= 11521


hpevtfParIsDisbleFrmBoot TRAP-TYPE
     ENTERPRISE hpIpfE0Events
     VARIABLES { hpIpfEvtDetailStr }
     DESCRIPTION
        "The fPar whose ID is identified in the event detail is disabled from booting because it has no bootable, healthy CPU. It may not own any CPU or the CPUs it owns are Unhealthy (or deconfigured)"

     --#SUMMARY "The fPar whose ID is identified in the event detail is disabled from booting because it has no bootable, healthy CPU. It may not own any CPU or the CPUs it owns are Unhealthy (or deconfigured)"
     --#ARGUMENTS {}
     --#SEVERITY WARNING
     --#TIMEINDEX 100
     --#STATE OPERATIONAL
::= 11529


hpevtfParNotInstantiateFW TRAP-TYPE
     ENTERPRISE hpIpfE0Events
     VARIABLES { hpIpfEvtDetailStr }
     DESCRIPTION
        "Non-critical event announces that an fPar is enabled to boot but has inadequate memory resources to instantiate the firmware for the fPar. The configuration is modified to disable but not delete this fPar."

     --#SUMMARY "Non-critical event announces that an fPar is enabled to boot but has inadequate memory resources to instantiate the firmware for the fPar. The configuration is modified to disable but not delete this fPar."
     --#ARGUMENTS {}
     --#SEVERITY WARNING
     --#TIMEINDEX 100
     --#STATE OPERATIONAL
::= 11530


hpevtfParNotHaveIOResrc TRAP-TYPE
     ENTERPRISE hpIpfE0Events
     VARIABLES { hpIpfEvtDetailStr }
     DESCRIPTION
        "The fPar has been enabled to boot, and contains at least one CPU and adequate memory but has not been given any IO resources. The soft partition (fPar) may therefore only boot as far as the EFI shell. It must be reconfigured and reset before it may boot an operating system."

     --#SUMMARY "The fPar has been enabled to boot, and contains at least one CPU and adequate memory but has not been given any IO resources. It must be reconfigured and reset before it may boot an operating system."
     --#ARGUMENTS {}
     --#SEVERITY WARNING
     --#TIMEINDEX 100
     --#STATE OPERATIONAL
::= 11531


hpevtCPUsDeconfig TRAP-TYPE
     ENTERPRISE hpIpfE0Events
     VARIABLES { hpIpfEvtDetailStr }
     DESCRIPTION
        "All CPUs were scheduled to be deconfigured"

     --#SUMMARY "All processors are scheduled for deconfiguration."
     --#ARGUMENTS {}
     --#SEVERITY WARNING
     --#TIMEINDEX 100
     --#STATE OPERATIONAL
::= 11537


hpevtCPUsReconfig TRAP-TYPE
     ENTERPRISE hpIpfE0Events
     VARIABLES { hpIpfEvtDetailStr }
     DESCRIPTION
        "All CPUs have been auto reconfigured"

     --#SUMMARY "Processors have been reconfigured due to installation of a new processor type, or SFW revision change."
     --#ARGUMENTS {}
     --#SEVERITY WARNING
     --#TIMEINDEX 100
     --#STATE OPERATIONAL
::= 11538


hpevtIOBckPln33VFail TRAP-TYPE
     ENTERPRISE hpIpfE0Events
     VARIABLES { hpIpfEvtDetailStr }
     DESCRIPTION
        "IO Backplane 3.3V power fault"

     --#SUMMARY "IO Backplane 3.3V power fault"
     --#ARGUMENTS {}
     --#SEVERITY CRITICAL
     --#TIMEINDEX 100
     --#STATE OPERATIONAL
::= 11566


hpevtBckPln5VFail TRAP-TYPE
     ENTERPRISE hpIpfE0Events
     VARIABLES { hpIpfEvtDetailStr }
     DESCRIPTION
        "IO Backplane 5.0V power fault"

     --#SUMMARY "IO Backplane 5.0V power fault"
     --#ARGUMENTS {}
     --#SEVERITY CRITICAL
     --#TIMEINDEX 100
     --#STATE OPERATIONAL
::= 11567


hpevtIOBckPlnNeg12VFail TRAP-TYPE
     ENTERPRISE hpIpfE0Events
     VARIABLES { hpIpfEvtDetailStr }
     DESCRIPTION
        "IO Backplane -12V power fault"

     --#SUMMARY "IO Backplane -12V power fault"
     --#ARGUMENTS {}
     --#SEVERITY CRITICAL
     --#TIMEINDEX 100
     --#STATE OPERATIONAL
::= 11568


hpevtIOBckPln12VFail TRAP-TYPE
     ENTERPRISE hpIpfE0Events
     VARIABLES { hpIpfEvtDetailStr }
     DESCRIPTION
        "IO Backplane +12V power fault"

     --#SUMMARY "IO Backplane +12V power fault"
     --#ARGUMENTS {}
     --#SEVERITY CRITICAL
     --#TIMEINDEX 100
     --#STATE OPERATIONAL
::= 11569


hpevtIOBckPln15VTempFail TRAP-TYPE
     ENTERPRISE hpIpfE0Events
     VARIABLES { hpIpfEvtDetailStr }
     DESCRIPTION
        "IO Backplane 1.5V temperature fault"

     --#SUMMARY "IO Backplane 1.5V temperature fault"
     --#ARGUMENTS {}
     --#SEVERITY CRITICAL
     --#TIMEINDEX 100
     --#STATE OPERATIONAL
::= 11575


hpevtIOBckPln33VTempFail TRAP-TYPE
     ENTERPRISE hpIpfE0Events
     VARIABLES { hpIpfEvtDetailStr }
     DESCRIPTION
        "IO Backplane 3.3V temperature fault"

     --#SUMMARY "IO Backplane 3.3V temperature fault"
     --#ARGUMENTS {}
     --#SEVERITY CRITICAL
     --#TIMEINDEX 100
     --#STATE OPERATIONAL
::= 11576


hpevtIOBckPlnNeg12VTempFail TRAP-TYPE
     ENTERPRISE hpIpfE0Events
     VARIABLES { hpIpfEvtDetailStr }
     DESCRIPTION
        "IO Backplane -12.0V temperature fault"

     --#SUMMARY "IO Backplane -12.0V temperature fault"
     --#ARGUMENTS {}
     --#SEVERITY CRITICAL
     --#TIMEINDEX 100
     --#STATE OPERATIONAL
::= 11578


hpevtIOBckPln12VTempFail TRAP-TYPE
     ENTERPRISE hpIpfE0Events
     VARIABLES { hpIpfEvtDetailStr }
     DESCRIPTION
        "IO Backplane +12.0V temperature fault"

     --#SUMMARY "IO Backplane +12.0V temperature fault"
     --#ARGUMENTS {}
     --#SEVERITY CRITICAL
     --#TIMEINDEX 100
     --#STATE OPERATIONAL
::= 11579


hpevtLocCelUnablClrLnkOffBit TRAP-TYPE
     ENTERPRISE hpIpfE0Events
     VARIABLES { hpIpfEvtDetailStr }
     DESCRIPTION
        "The local cell was unable to clear the link_off bit on at least one CC-CC link.
Data field: return value of Phase3BackToBackPrep()"

     --#SUMMARY "The local cell was unable to clear the link_off bit on at least one CC-CC link.  Data field: return value of Phase3BackToBackPrep()"
     --#ARGUMENTS {}
     --#SEVERITY WARNING
     --#TIMEINDEX 100
     --#STATE OPERATIONAL
::= 11580


hpevtArfOlaPreRendezUnablRchCel TRAP-TYPE
     ENTERPRISE hpIpfE0Events
     VARIABLES { hpIpfEvtDetailStr }
     DESCRIPTION
        "ArfOLAPreRendez() was unable to reach the added cell.
Data field: bitmap of unreachable cells"

     --#SUMMARY "ArfOLAPreRendez() was unable to reach the added cell.  Data field: bitmap of unreachable cells"
     --#ARGUMENTS {}
     --#SEVERITY WARNING
     --#TIMEINDEX 100
     --#STATE OPERATIONAL
::= 11581


hpevtUnexpctErrSetNctTbl TRAP-TYPE
     ENTERPRISE hpIpfE0Events
     VARIABLES { hpIpfEvtDetailStr }
     DESCRIPTION
        "An unexpected error occurred in SetupNCTable().
Data field: return value from SetupNCTable()"

     --#SUMMARY "An unexpected error occurred in SetupNCTable().  Data field: return value from SetupNCTable()."
     --#ARGUMENTS {}
     --#SEVERITY WARNING
     --#TIMEINDEX 100
     --#STATE OPERATIONAL
::= 11582


hpevtPhs4UnexpctFail TRAP-TYPE
     ENTERPRISE hpIpfE0Events
     VARIABLES { hpIpfEvtDetailStr }
     DESCRIPTION
        "Phase4BackToBackPrep() unexpectedly failed.
Data field: return value of Phase4BackToBackPrep()"

     --#SUMMARY "Phase4BackToBackPrep() unexpectedly failed.  Data field: return value of Phase4BackToBackPrep()"
     --#ARGUMENTS {}
     --#SEVERITY WARNING
     --#TIMEINDEX 100
     --#STATE OPERATIONAL
::= 11583


hpevtUnablSyncGrphCell TRAP-TYPE
     ENTERPRISE hpIpfE0Events
     VARIABLES { hpIpfEvtDetailStr }
     DESCRIPTION
        "Data field: (master cell number << 56) | (bitmap of cells to synch)"

     --#SUMMARY "Unable to synch graphs between all cells in the partition after an OLA.  Data field: (master cell number  56) | (bitmap of cells to synch)."
     --#ARGUMENTS {}
     --#SEVERITY WARNING
     --#TIMEINDEX 100
     --#STATE OPERATIONAL
::= 11584


hpevtBitMapUnrchCel TRAP-TYPE
     ENTERPRISE hpIpfE0Events
     VARIABLES { hpIpfEvtDetailStr }
     DESCRIPTION
        "Data field: bitmap of unreachable cells."

     --#SUMMARY "Data field: bitmap of unreachable cells."
     --#ARGUMENTS {}
     --#SEVERITY WARNING
     --#TIMEINDEX 100
     --#STATE OPERATIONAL
::= 11585


hpevtRetValNctCohTbl TRAP-TYPE
     ENTERPRISE hpIpfE0Events
     VARIABLES { hpIpfEvtDetailStr }
     DESCRIPTION
        "Data field: return value from SetupNCTable() or SetupCohTable()"

     --#SUMMARY "An unexpected error occurred while setting up the Non-Coherent or Coherent tables after an OLA.  Data field: return value from SetupNCTable() or SetupCohTable()"
     --#ARGUMENTS {}
     --#SEVERITY WARNING
     --#TIMEINDEX 100
     --#STATE OPERATIONAL
::= 11586


hpevtArfRoutEnblRetErrLocCel TRAP-TYPE
     ENTERPRISE hpIpfE0Events
     VARIABLES { hpIpfEvtDetailStr }
     DESCRIPTION
        "Data field: (local cell number << 56) | (bitmap of routes to enable)"

     --#SUMMARY "ArfRouteEnable() returned an unexpected error while enabling routes to the local cell.  Data field: (local cell number  56) | (bitmap of routes to enable)"
     --#ARGUMENTS {}
     --#SEVERITY WARNING
     --#TIMEINDEX 100
     --#STATE OPERATIONAL
::= 11597


hpevtArfRoutDisRetErrOla TRAP-TYPE
     ENTERPRISE hpIpfE0Events
     VARIABLES { hpIpfEvtDetailStr }
     DESCRIPTION
        "Data field: (bitmap of cells << 32) | (bitmap of routes to disable)"

     --#SUMMARY "ArfRouteDiable() returned an unexpected error while disabling routes during an OLA operation.  Data field: (bitmap of cells  32) | (bitmap of routes to disable)"
     --#ARGUMENTS {}
     --#SEVERITY WARNING
     --#TIMEINDEX 100
     --#STATE OPERATIONAL
::= 11598


hpevtArfRoutDisRetErrArfPhs4 TRAP-TYPE
     ENTERPRISE hpIpfE0Events
     VARIABLES { hpIpfEvtDetailStr }
     DESCRIPTION
        "Data field: (bitmap of source cells << 32) | (bitmap of routes to disable)"

     --#SUMMARY "ArfRouteDiable() returned an unexpected error while disabling routes in ArfPhase4.  Data field: (bitmap of source cells  32) | (bitmap of routes to disable)."
     --#ARGUMENTS {}
     --#SEVERITY WARNING
     --#TIMEINDEX 100
     --#STATE OPERATIONAL
::= 11599


hpevtMemAlloctFail TRAP-TYPE
     ENTERPRISE hpIpfE0Events
     VARIABLES { hpIpfEvtDetailStr }
     DESCRIPTION
        "Memory allocation failed.  The data is the size of the memory block which could not be allocated."

     --#SUMMARY "Memory allocation failed.  The data is the size of the memory block which could not be allocated"
     --#ARGUMENTS {}
     --#SEVERITY CRITICAL
     --#TIMEINDEX 100
     --#STATE OPERATIONAL
::= 11603


hpevtMemLockFail TRAP-TYPE
     ENTERPRISE hpIpfE0Events
     VARIABLES { hpIpfEvtDetailStr }
     DESCRIPTION
        "Memory locking failed.  The data is the size of the memory block which could not be locked."

     --#SUMMARY "Memory locking failed.  The data is the size of the memory block which could not be locked"
     --#ARGUMENTS {}
     --#SEVERITY CRITICAL
     --#TIMEINDEX 100
     --#STATE OPERATIONAL
::= 11604


hpevtMinProcReqMoreThanAvail TRAP-TYPE
     ENTERPRISE hpIpfE0Events
     VARIABLES { hpIpfEvtDetailStr }
     DESCRIPTION
        "The minimum number of processors required is more than the number available.  The data is the number of available processors."

     --#SUMMARY "The minimum number of processors required is more than the number available.  The data is the number of available processors"
     --#ARGUMENTS {}
     --#SEVERITY CRITICAL
     --#TIMEINDEX 100
     --#STATE OPERATIONAL
::= 11605


hpevtSyntErrReadConfig TRAP-TYPE
     ENTERPRISE hpIpfE0Events
     VARIABLES { hpIpfEvtDetailStr }
     DESCRIPTION
        "A syntax error was found while reading the configuration file.  The data is the line number of the line where the error was discovered."

     --#SUMMARY "A syntax error was found while reading the configuration file.  The data is the line number of the line where the error was discovered."
     --#ARGUMENTS {}
     --#SEVERITY CRITICAL
     --#TIMEINDEX 100
     --#STATE OPERATIONAL
::= 11606


hpevtVMNotHandlGuestOSPerf TRAP-TYPE
     ENTERPRISE hpIpfE0Events
     VARIABLES { hpIpfEvtDetailStr }
     DESCRIPTION
        "The guest operating system performed an operation which could not be handled by the virtual machine.  The virtual machine could not continue running the guest so it stopped."

     --#SUMMARY "The guest operating system performed an operation which could not be handled by the virtual machine.  The virtual machine could not continue running the guest so it stopped."
     --#ARGUMENTS {}
     --#SEVERITY CRITICAL
     --#TIMEINDEX 100
     --#STATE OPERATIONAL
::= 11607


hpevtKernlDrvFailLckMem TRAP-TYPE
     ENTERPRISE hpIpfE0Events
     VARIABLES { hpIpfEvtDetailStr }
     DESCRIPTION
        "Kernel driver failed to lock memory"

     --#SUMMARY "Kernel driver failed to lock memory"
     --#ARGUMENTS {}
     --#SEVERITY CRITICAL
     --#TIMEINDEX 100
     --#STATE OPERATIONAL
::= 11696


hpevtMMIOmapFndInfoInTble TRAP-TYPE
     ENTERPRISE hpIpfE0Events
     VARIABLES { hpIpfEvtDetailStr }
     DESCRIPTION
        "The code which initializes the MMIO/IOP map found that the table already contained information."

     --#SUMMARY "The code which initializes the MMIO/IOP map found that the table already contained information."
     --#ARGUMENTS {}
     --#SEVERITY CRITICAL
     --#TIMEINDEX 100
     --#STATE OPERATIONAL
::= 11700


hpevtAttmptAddPCImoreThanAllow TRAP-TYPE
     ENTERPRISE hpIpfE0Events
     VARIABLES { hpIpfEvtDetailStr }
     DESCRIPTION
        "An attempt was made to add a PCI bus whith a number greater than the maximum allowed."

     --#SUMMARY "An attempt was made to add a PCI bus whith a number greater than the maximum allowed."
     --#ARGUMENTS {}
     --#SEVERITY CRITICAL
     --#TIMEINDEX 100
     --#STATE OPERATIONAL
::= 11702


hpevtCPUConfigNotSupprt TRAP-TYPE
     ENTERPRISE hpIpfE0Events
     VARIABLES { hpIpfEvtDetailStr }
     DESCRIPTION
        "The configured CPU generation is not supported"

     --#SUMMARY "The configured CPU generation is not supported"
     --#ARGUMENTS {}
     --#SEVERITY CRITICAL
     --#TIMEINDEX 100
     --#STATE OPERATIONAL
::= 11703


hpevtISAUARTcreatWithoutDatStrct TRAP-TYPE
     ENTERPRISE hpIpfE0Events
     VARIABLES { hpIpfEvtDetailStr }
     DESCRIPTION
        "An ISA UART was created without a data structure.  A PCI UART structure exists"

     --#SUMMARY "An ISA UART was created without a data structure.  A PCI UART structure exists"
     --#ARGUMENTS {}
     --#SEVERITY CRITICAL
     --#TIMEINDEX 100
     --#STATE OPERATIONAL
::= 11705


hpevtTCGETorIOCTLFail TRAP-TYPE
     ENTERPRISE hpIpfE0Events
     VARIABLES { hpIpfEvtDetailStr }
     DESCRIPTION
        "A TCGETS or TCSETS IOCTL failed.  The errno status will be in a subsequent event."

     --#SUMMARY "A TCGETS or TCSETS IOCTL failed.  The errno status will be in a subsequent event."
     --#ARGUMENTS {}
     --#SEVERITY CRITICAL
     --#TIMEINDEX 100
     --#STATE OPERATIONAL
::= 11706


hpevtStatCallPMANFail TRAP-TYPE
     ENTERPRISE hpIpfE0Events
     VARIABLES { hpIpfEvtDetailStr }
     DESCRIPTION
        "A stat call on the PMAN failed.  The next event contains the failure errno."

     --#SUMMARY "A stat call on the PMAN failed.  The next event contains the failure errno."
     --#ARGUMENTS {}
     --#SEVERITY CRITICAL
     --#TIMEINDEX 100
     --#STATE OPERATIONAL
::= 11707


hpevtVMDrvNotOpen TRAP-TYPE
     ENTERPRISE hpIpfE0Events
     VARIABLES { hpIpfEvtDetailStr }
     DESCRIPTION
        "The virtual machine driver could not be opened"

     --#SUMMARY "The virtual machine driver could not be opened"
     --#ARGUMENTS {}
     --#SEVERITY CRITICAL
     --#TIMEINDEX 100
     --#STATE OPERATIONAL
::= 11708


hpevtVMDrvNotCreatVM TRAP-TYPE
     ENTERPRISE hpIpfE0Events
     VARIABLES { hpIpfEvtDetailStr }
     DESCRIPTION
        "The virtual machine driver could not create a virtual machine"

     --#SUMMARY "The virtual machine driver could not create a virtual machine"
     --#ARGUMENTS {}
     --#SEVERITY CRITICAL
     --#TIMEINDEX 100
     --#STATE OPERATIONAL
::= 11709


hpevtNotAbleCreatNodeForComm TRAP-TYPE
     ENTERPRISE hpIpfE0Events
     VARIABLES { hpIpfEvtDetailStr }
     DESCRIPTION
        "Could not create a file system node for communication between the vmm driver and the virtual machine.  The next event contains the error from the Unix system call."

     --#SUMMARY "Could not create a file system node for communication between the vmm driver and the virtual machine.  The next event contains the error from the Unix system call."
     --#ARGUMENTS {}
     --#SEVERITY CRITICAL
     --#TIMEINDEX 100
     --#STATE OPERATIONAL
::= 11710


hpevtVMNotOpen TRAP-TYPE
     ENTERPRISE hpIpfE0Events
     VARIABLES { hpIpfEvtDetailStr }
     DESCRIPTION
        "The vm device was created but cannot be opened"

     --#SUMMARY "The vm device was created but cannot be opened"
     --#ARGUMENTS {}
     --#SEVERITY CRITICAL
     --#TIMEINDEX 100
     --#STATE OPERATIONAL
::= 11711


hpevtVMDrvNotLoad TRAP-TYPE
     ENTERPRISE hpIpfE0Events
     VARIABLES { hpIpfEvtDetailStr }
     DESCRIPTION
        "The virtual machine driver has not been loaded"

     --#SUMMARY "The virtual machine driver has not been loaded"
     --#ARGUMENTS {}
     --#SEVERITY CRITICAL
     --#TIMEINDEX 100
     --#STATE OPERATIONAL
::= 11712


hpevtCreatThreadPMANFail TRAP-TYPE
     ENTERPRISE hpIpfE0Events
     VARIABLES { hpIpfEvtDetailStr }
     DESCRIPTION
        "An attempt to create a thread on the PMAN has failed.  The next event contains the Unix error number."

     --#SUMMARY "An attempt to create a thread on the PMAN has failed.  The next event contains the Unix error number."
     --#ARGUMENTS {}
     --#SEVERITY CRITICAL
     --#TIMEINDEX 100
     --#STATE OPERATIONAL
::= 11718


hpevtVMDrvUnableCommVM TRAP-TYPE
     ENTERPRISE hpIpfE0Events
     VARIABLES { hpIpfEvtDetailStr }
     DESCRIPTION
        "VM Driver was unable to communicate with virtual machine"

     --#SUMMARY "VM Driver was unable to communicate with virtual machine"
     --#ARGUMENTS {}
     --#SEVERITY CRITICAL
     --#TIMEINDEX 100
     --#STATE OPERATIONAL
::= 11719


hpevtConfigUnableToRd TRAP-TYPE
     ENTERPRISE hpIpfE0Events
     VARIABLES { hpIpfEvtDetailStr }
     DESCRIPTION
        "The configuration file could not be read"

     --#SUMMARY "The configuration file could not be read"
     --#ARGUMENTS {}
     --#SEVERITY CRITICAL
     --#TIMEINDEX 100
     --#STATE OPERATIONAL
::= 11720


hpevtMemAllocFWTblFail TRAP-TYPE
     ENTERPRISE hpIpfE0Events
     VARIABLES { hpIpfEvtDetailStr }
     DESCRIPTION
        "Memory allocation for a firmware table has failed.  The data
contains the name of the firmware table."

     --#SUMMARY "Memory allocation for a firmware table has failed.  The data contains the name of the firmware table."
     --#ARGUMENTS {}
     --#SEVERITY CRITICAL
     --#TIMEINDEX 100
     --#STATE OPERATIONAL
::= 11721


hpevtDrvUnableBldMapTbl TRAP-TYPE
     ENTERPRISE hpIpfE0Events
     VARIABLES { hpIpfEvtDetailStr }
     DESCRIPTION
        "Driver was unable to build map tables"

     --#SUMMARY "Driver was unable to build map tables"
     --#ARGUMENTS {}
     --#SEVERITY CRITICAL
     --#TIMEINDEX 100
     --#STATE OPERATIONAL
::= 11723


hpevtVMRebootFail TRAP-TYPE
     ENTERPRISE hpIpfE0Events
     VARIABLES { hpIpfEvtDetailStr }
     DESCRIPTION
        "Reboot failed.  The virtual machine will exit."

     --#SUMMARY "Reboot failed.  The virtual machine will exit."
     --#ARGUMENTS {}
     --#SEVERITY CRITICAL
     --#TIMEINDEX 100
     --#STATE OPERATIONAL
::= 11724


hpevtSetIntlCohTblRetErr TRAP-TYPE
     ENTERPRISE hpIpfE0Events
     VARIABLES { hpIpfEvtDetailStr }
     DESCRIPTION
        "Data field: (cell set << 32) | (return value from SetupInitialCohTables())"

     --#SUMMARY "SetupInitialCohTables() returned an error.  Data field: (cell set  32) | (return value from SetupInitialCohTables())."
     --#ARGUMENTS {}
     --#SEVERITY WARNING
     --#TIMEINDEX 100
     --#STATE OPERATIONAL
::= 11775


hpBootStblStoreFlashErr TRAP-TYPE
     ENTERPRISE hpIpfE0Events
     VARIABLES { hpIpfEvtDetailStr }
     DESCRIPTION
        "Stable store read or write to flash failed."

     --#SUMMARY "Stable store read or write to flash failed."
     --#ARGUMENTS {}
     --#SEVERITY WARNING
     --#TIMEINDEX 100
     --#STATE OPERATIONAL
::= 11780


hpBootStblStoreNvMErr TRAP-TYPE
     ENTERPRISE hpIpfE0Events
     VARIABLES { hpIpfEvtDetailStr }
     DESCRIPTION
        "Error reading or writing the stable store NVM area"

     --#SUMMARY "Error reading or writing the stable store NVM area"
     --#ARGUMENTS {}
     --#SEVERITY WARNING
     --#TIMEINDEX 100
     --#STATE OPERATIONAL
::= 11783


hpevtFWDetectilleglMemConfig TRAP-TYPE
     ENTERPRISE hpIpfE0Events
     VARIABLES { hpIpfEvtDetailStr }
     DESCRIPTION
        "SFW has detected an illegal memory config using 4GB DIMMs.  The system will be halted"

     --#SUMMARY "FW has detected an illegal memory config using 4GB DIMMs.  The system will be halted."
     --#ARGUMENTS {}
     --#SEVERITY CRITICAL
     --#TIMEINDEX 100
     --#STATE OPERATIONAL
::= 11784


hpevtSFWFailAllotNVM TRAP-TYPE
     ENTERPRISE hpIpfE0Events
     VARIABLES { hpIpfEvtDetailStr }
     DESCRIPTION
        "SFW component NVM space is not big enough to store all it data.  Check the
ASCII data field to determine which component caused the error."

     --#SUMMARY "SFW failed to allocate enough NVM to store all required data."
     --#ARGUMENTS {}
     --#SEVERITY WARNING
     --#TIMEINDEX 100
     --#STATE OPERATIONAL
::= 11788


hpevtSFWFailAllotSCRRAM TRAP-TYPE
     ENTERPRISE hpIpfE0Events
     VARIABLES { hpIpfEvtDetailStr }
     DESCRIPTION
        "SFW component does not
allocate enough SCR ram
space to store it data."

     --#SUMMARY "SFW failed to allocate enough SCR RAM to store all required data."
     --#ARGUMENTS {}
     --#SEVERITY WARNING
     --#TIMEINDEX 100
     --#STATE OPERATIONAL
::= 11789


hpevtSetIntlCohRetErrArfPhs3 TRAP-TYPE
     ENTERPRISE hpIpfE0Events
     VARIABLES { hpIpfEvtDetailStr }
     DESCRIPTION
        "Data field: cell set [63:32], return value [31:0]"

     --#SUMMARY "SetupIntialCohTables() returned an error in ArfPhase3.  Data field: cell set [63:32], return value [31:0]"
     --#ARGUMENTS {}
     --#SEVERITY WARNING
     --#TIMEINDEX 100
     --#STATE OPERATIONAL
::= 11797


hpevtErrWrtErrMskAlrecAlTran TRAP-TYPE
     ENTERPRISE hpIpfE0Events
     VARIABLES { hpIpfEvtDetailStr }
     DESCRIPTION
        "Data field: cell ID [63:56], port num [55:44], XBC ID [43:32]"

     --#SUMMARY "Error writing the error masks for ALREC and ALTRAN.  Data field: cell ID [63:56], port num [55:44], XBC ID [43:32]"
     --#ARGUMENTS {}
     --#SEVERITY WARNING
     --#TIMEINDEX 100
     --#STATE OPERATIONAL
::= 11807


hpevtFwUnexpctIntrnlErrVertx TRAP-TYPE
     ENTERPRISE hpIpfE0Events
     VARIABLES { hpIpfEvtDetailStr }
     DESCRIPTION
        "Data field:  vType1 [63:56] | vPort1 [55:48] | vId1 [47:32] |
                  vType2 [31:24] | vPort2 [23:16] | vId2 [15:0]"

     --#SUMMARY "Firmware had an unexpected internal error from the vertex module..  Data field:  vType1 [63:56] | vPort1 [55:48] | vId1 [47:32] | vType2 [31:24] | vPort2 [23:16] | vId2 [15:0]"
     --#ARGUMENTS {}
     --#SEVERITY WARNING
     --#TIMEINDEX 100
     --#STATE OPERATIONAL
::= 11840


hpOsUnsupportedWmixedCpuRevs TRAP-TYPE
     ENTERPRISE hpIpfE0Events
     VARIABLES { hpIpfEvtDetailStr }
     DESCRIPTION
        "The OS being booted is not supported in a partition containing a mix of processor stepping revisions."

     --#SUMMARY "The OS being booted is not supported in a partition containing a mix of processor stepping revisions."
     --#ARGUMENTS {}
     --#SEVERITY CRITICAL
     --#TIMEINDEX 100
     --#STATE OPERATIONAL
::= 11850


hpevtFwUnexpctErrSetLnk TRAP-TYPE
     ENTERPRISE hpIpfE0Events
     VARIABLES { hpIpfEvtDetailStr }
     DESCRIPTION
        "Data field:  vType1 [63:56] | vPort1 [55:48] | vId1 [47:32] |
                  vType2 [31:24] | vPort2 [23:16] | vId2 [15:0]"

     --#SUMMARY "Firmware had an unexpected error while setting up links.  Data field:  vType1 [63:56] | vPort1 [55:48] | vId1 [47:32] | vType2 [31:24] | vPort2 [23:16] | vId2 [15:0]"
     --#ARGUMENTS {}
     --#SEVERITY WARNING
     --#TIMEINDEX 100
     --#STATE OPERATIONAL
::= 11851


hpevtFwUnbleWrtSkyGlobLnkSelCoh TRAP-TYPE
     ENTERPRISE hpIpfE0Events
     VARIABLES { hpIpfEvtDetailStr }
     DESCRIPTION
        "Data field: cell num [63:56] | link sel coh CSR (0 or 1) [0:0]"

     --#SUMMARY "Firmware was unable to write the Skyline global LINK_SEL_COHx CSR.  Data field: cell num [63:56] | link sel coh CSR (0 or 1) [0:0]"
     --#ARGUMENTS {}
     --#SEVERITY WARNING
     --#TIMEINDEX 100
     --#STATE OPERATIONAL
::= 11863


hpOsBootDisabledWmixedCpuKeys TRAP-TYPE
     ENTERPRISE hpIpfE0Events
     VARIABLES { hpIpfEvtDetailStr }
     DESCRIPTION
        "The OS suitable for booting in this mode does not support booting in the current configuration due to the existence of cpus of differing revisions."

     --#SUMMARY "The requested OS does not support booting with mixed CPU revisions"
     --#ARGUMENTS {}
     --#SEVERITY WARNING
     --#TIMEINDEX 100
     --#STATE OPERATIONAL
::= 11870


hpevtSysFwErrUpdtLnk TRAP-TYPE
     ENTERPRISE hpIpfE0Events
     VARIABLES { hpIpfEvtDetailStr }
     DESCRIPTION
        "System firmware experienced an error while updating the link sel value.  Data field indicates return status"

     --#SUMMARY "System firmware experienced an error while updating the link sel value.  Data field indicates return status."
     --#ARGUMENTS {}
     --#SEVERITY WARNING
     --#TIMEINDEX 100
     --#STATE OPERATIONAL
::= 11885


hpevtFabUnablGenSkyCsrAddr TRAP-TYPE
     ENTERPRISE hpIpfE0Events
     VARIABLES { hpIpfEvtDetailStr }
     DESCRIPTION
        "Fabric was unable to generate a Skyline CSR address
Data field: cell number [63:56] and return value from address function [31:0]"

     --#SUMMARY "Fabric was unable to generate a Skyline CSR address.  Data field: cell number [63:56] and return value from address function [31:0]."
     --#ARGUMENTS {}
     --#SEVERITY WARNING
     --#TIMEINDEX 100
     --#STATE OPERATIONAL
::= 11904


hpevtFwUnablGenSkyCsrAdrr TRAP-TYPE
     ENTERPRISE hpIpfE0Events
     VARIABLES { hpIpfEvtDetailStr }
     DESCRIPTION
        "Firmware was unable to generate a Skyline CSR address.
Data field: cell number [63:56] | return value [31:0]"

     --#SUMMARY "Firmware was unable to generate a Skyline CSR address.  Data field: cell number [63:56] | return value [31:0]."
     --#ARGUMENTS {}
     --#SEVERITY WARNING
     --#TIMEINDEX 100
     --#STATE OPERATIONAL
::= 11905


hpevtNoOSBootRendez TRAP-TYPE
     ENTERPRISE hpIpfE0Events
     VARIABLES { hpIpfEvtDetailStr }
     DESCRIPTION
        "Target CPU receives wakeup interrupt to join the OS but the OS_BOOT_RENDEZ entry point is invalid or none-existent"

     --#SUMMARY "Invalid or no OS boot rendezvous entry point for target CPU"
     --#ARGUMENTS {}
     --#SEVERITY CRITICAL
     --#TIMEINDEX 100
     --#STATE OPERATIONAL
::= 11932


hpevtChksmFailOSBootRendez TRAP-TYPE
     ENTERPRISE hpIpfE0Events
     VARIABLES { hpIpfEvtDetailStr }
     DESCRIPTION
        "The entry  point for OS_BOOT_RENDEZ exists, but fails the checksum test performed by firmware"

     --#SUMMARY "Checksum verification failed for OS_BOOT_RENDEZ entry point"
     --#ARGUMENTS {}
     --#SEVERITY CRITICAL
     --#TIMEINDEX 100
     --#STATE OPERATIONAL
::= 11933


hpevtSysFWCallPalCopyInfoFail TRAP-TYPE
     ENTERPRISE hpIpfE0Events
     VARIABLES { hpIpfEvtDetailStr }
     DESCRIPTION
        "The System Firmware call to PAL_COPY_INFO failed."

     --#SUMMARY "The System Firmware call to PAL_COPY_INFO failed."
     --#ARGUMENTS {}
     --#SEVERITY WARNING
     --#TIMEINDEX 100
     --#STATE OPERATIONAL
::= 11960


hpevtSysFWCallPalCopyPalFail TRAP-TYPE
     ENTERPRISE hpIpfE0Events
     VARIABLES { hpIpfEvtDetailStr }
     DESCRIPTION
        "The System Firmware call to PAL_COPY_PAL failed."

     --#SUMMARY "The System Firmware call to PAL_COPY_PAL failed."
     --#ARGUMENTS {}
     --#SEVERITY WARNING
     --#TIMEINDEX 100
     --#STATE OPERATIONAL
::= 11961


hpevtSysFWCallPalCacFlusFail TRAP-TYPE
     ENTERPRISE hpIpfE0Events
     VARIABLES { hpIpfEvtDetailStr }
     DESCRIPTION
        "The System Firmware call to PAL_CACHE_FLUSH failed."

     --#SUMMARY "The System Firmware call to PAL_CACHE_FLUSH failed."
     --#ARGUMENTS {}
     --#SEVERITY WARNING
     --#TIMEINDEX 100
     --#STATE OPERATIONAL
::= 11962


hpevtCellNotInit TRAP-TYPE
     ENTERPRISE hpIpfE0Events
     VARIABLES { hpIpfEvtDetailStr }
     DESCRIPTION
        "Cell on line add/delete is not initialized and cannot be used."

     --#SUMMARY "Cell on line add/delete is not initialized"
     --#ARGUMENTS {}
     --#SEVERITY CRITICAL
     --#TIMEINDEX 100
     --#STATE OPERATIONAL
::= 11964


hpevtFPARsCompBroke TRAP-TYPE
     ENTERPRISE hpIpfE0Events
     VARIABLES { hpIpfEvtDetailStr }
     DESCRIPTION
        "In FPARs mode, cell on line add/delete depends on functionality in the FPARs component.  This is either broken or missing."

     --#SUMMARY "An FPARs component on which cell on-line add/delete depends is broken or missing."
     --#ARGUMENTS {}
     --#SEVERITY CRITICAL
     --#TIMEINDEX 100
     --#STATE OPERATIONAL
::= 11966


hpevtFailGetFPARsSemphr TRAP-TYPE
     ENTERPRISE hpIpfE0Events
     VARIABLES { hpIpfEvtDetailStr }
     DESCRIPTION
        "Cell on line add/delete in FPARs mode failed to get the FPARs semaphore."

     --#SUMMARY "Cell on-line add/delete in FPARs mode failed to get the FPARs semaphore."
     --#ARGUMENTS {}
     --#SEVERITY CRITICAL
     --#TIMEINDEX 100
     --#STATE OPERATIONAL
::= 11967


hpevtMorThnOneProcCallCell TRAP-TYPE
     ENTERPRISE hpIpfE0Events
     VARIABLES { hpIpfEvtDetailStr }
     DESCRIPTION
        "More than one processor from an FPAR called into cell on line add/delete"

     --#SUMMARY "More than one processor from an FPAR called into cell on-line add/delete"
     --#ARGUMENTS {}
     --#SEVERITY CRITICAL
     --#TIMEINDEX 100
     --#STATE OPERATIONAL
::= 11968


hpevtFPARsProcFailRendez TRAP-TYPE
     ENTERPRISE hpIpfE0Events
     VARIABLES { hpIpfEvtDetailStr }
     DESCRIPTION
        "All FPARs processors failed to rendezvous during a cell on line add/delete op"

     --#SUMMARY "All FPARs processors failed to rendezvous during a cell on line add/delete operation"
     --#ARGUMENTS {}
     --#SEVERITY CRITICAL
     --#TIMEINDEX 100
     --#STATE OPERATIONAL
::= 11969


hpevtEncntUnexptErrOLA TRAP-TYPE
     ENTERPRISE hpIpfE0Events
     VARIABLES { hpIpfEvtDetailStr }
     DESCRIPTION
        "Unable to setup Skyline LINK_SEL_COHx CSRs on the running partition to the newly added cell.
Data field: cell set [63:32] | return val [31:0]"

     --#SUMMARY "Encountered unexpected error during cell OLA activity."
     --#ARGUMENTS {}
     --#SEVERITY WARNING
     --#TIMEINDEX 100
     --#STATE OPERATIONAL
::= 11970


hpevtMCAOccPriorPreMCA TRAP-TYPE
     ENTERPRISE hpIpfE0Events
     VARIABLES { hpIpfEvtDetailStr }
     DESCRIPTION
        "This indicates an MCA happening before a previous MCA was not completely handled."

     --#SUMMARY "MCA  occurred prior to completion of previous MCA."
     --#ARGUMENTS {}
     --#SEVERITY WARNING
     --#TIMEINDEX 100
     --#STATE OPERATIONAL
::= 11971


hpevtMCAInitEvtProc TRAP-TYPE
     ENTERPRISE hpIpfE0Events
     VARIABLES { hpIpfEvtDetailStr }
     DESCRIPTION
        "This indicates an MCA event happening before a previous INIT event was not completely processed."

     --#SUMMARY "MCA during init event processing"
     --#ARGUMENTS {}
     --#SEVERITY WARNING
     --#TIMEINDEX 100
     --#STATE OPERATIONAL
::= 11972


hpevtUnablFndBadEdg TRAP-TYPE
     ENTERPRISE hpIpfE0Events
     VARIABLES { hpIpfEvtDetailStr }
     DESCRIPTION
        "Firmware was unable to find a bad edge in an untraversable route.  Data Field: (destCell << 56 | port num < 44 | xbc num << 32 | return status)"

     --#SUMMARY "unable to find a bad edge in an untraversable route"
     --#ARGUMENTS {}
     --#SEVERITY WARNING
     --#TIMEINDEX 100
     --#STATE OPERATIONAL
::= 11974


hpevtUnknEntityDrwPwrBus TRAP-TYPE
     ENTERPRISE hpIpfE0Events
     VARIABLES { hpIpfEvtDetailStr }
     DESCRIPTION
        "Some entity that is not known to the firmware, is drawing power from the bus bars."

     --#SUMMARY "Unknown entity drawing power from bus bars."
     --#ARGUMENTS {}
     --#SEVERITY WARNING
     --#TIMEINDEX 100
     --#STATE OPERATIONAL
::= 11989


hpevtSoftPartNotBoot TRAP-TYPE
     ENTERPRISE hpIpfE0Events
     VARIABLES { hpIpfEvtDetailStr }
     DESCRIPTION
        "Rebooting the partition to nPars because a soft partition could not be booted."

     --#SUMMARY "Soft partition could not be booted, reverting to nPars."
     --#ARGUMENTS {}
     --#SEVERITY CRITICAL
     --#TIMEINDEX 100
     --#STATE OPERATIONAL
::= 12001


hpevtUnablRotArndBrkLnk TRAP-TYPE
     ENTERPRISE hpIpfE0Events
     VARIABLES { hpIpfEvtDetailStr }
     DESCRIPTION
        "Firmware was unable to find a replacement route for the broken link.  Data field contains: port << 44, chip id << 32, and number of attempts to find an alternate route"

     --#SUMMARY "Unable to route around broken link."
     --#ARGUMENTS {}
     --#SEVERITY WARNING
     --#TIMEINDEX 100
     --#STATE OPERATIONAL
::= 12008


hpevtUnablSetAPERLock TRAP-TYPE
     ENTERPRISE hpIpfE0Events
     VARIABLES { hpIpfEvtDetailStr }
     DESCRIPTION
        "Data field details the cell that failed to set its bit"

     --#SUMMARY "Unable to set the APER "fabric lockdown" bit"
     --#ARGUMENTS {}
     --#SEVERITY WARNING
     --#TIMEINDEX 100
     --#STATE OPERATIONAL
::= 12013


hpevtUncorrtMemEccErrOccr TRAP-TYPE
     ENTERPRISE hpIpfE0Events
     VARIABLES { hpIpfEvtDetailStr }
     DESCRIPTION
        "Indicates that an uncorrectable ECC error has been encountered, and gives the physical location of the DIMM that had the error."

     --#SUMMARY "An uncorrectable memory ECC error has occurred. The data field gives the physical location of the DIMM that had the error"
     --#ARGUMENTS {}
     --#SEVERITY CRITICAL
     --#TIMEINDEX 100
     --#STATE OPERATIONAL
::= 12017


hpevtErrRetrvCrssbarLnk TRAP-TYPE
     ENTERPRISE hpIpfE0Events
     VARIABLES { hpIpfEvtDetailStr }
     DESCRIPTION
        "System firmware experienced an error while retrieving the expected neighbor fabric chip for distributing traffic over crossbarl inks.  Data Field: (xbc port # << 44) | (xbc # << 32) | return status"

     --#SUMMARY "An error encountered while retrieving the expected neighbor fabric chip for distributing traffic over crossbar links."
     --#ARGUMENTS {}
     --#SEVERITY WARNING
     --#TIMEINDEX 100
     --#STATE OPERATIONAL
::= 12025


hpevtUnablRdCrssbar TRAP-TYPE
     ENTERPRISE hpIpfE0Events
     VARIABLES { hpIpfEvtDetailStr }
     DESCRIPTION
        "Could not read crossbar neighbor information during routing.  Data Field: (xbc port << 44) | (xbc << 32) | error status"

     --#SUMMARY "Could not read crossbar neighbor information during routing."
     --#ARGUMENTS {}
     --#SEVERITY WARNING
     --#TIMEINDEX 100
     --#STATE OPERATIONAL
::= 12028


hpevtUnablEstbshCrssbar TRAP-TYPE
     ENTERPRISE hpIpfE0Events
     VARIABLES { hpIpfEvtDetailStr }
     DESCRIPTION
        "Could not establish route for local crossbar during route around routing.  Data Field: (xbc port << 44) | (xbc << 32) | error status"

     --#SUMMARY "Could not establish route for local crossbar during route around routing."
     --#ARGUMENTS {}
     --#SEVERITY WARNING
     --#TIMEINDEX 100
     --#STATE OPERATIONAL
::= 12029


hpevtNoRoutLocCrssBar TRAP-TYPE
     ENTERPRISE hpIpfE0Events
     VARIABLES { hpIpfEvtDetailStr }
     DESCRIPTION
        "An invalid TPM has been detected in the system and is being use. Security might be compromised.
Data field unused."

     --#SUMMARY "Could not establish route for local crossbar during route around routin"
     --#ARGUMENTS {}
     --#SEVERITY CRITICAL
     --#TIMEINDEX 100
     --#STATE OPERATIONAL
::= 12047


hpevtInvalidTPM TRAP-TYPE
     ENTERPRISE hpIpfE0Events
     VARIABLES { hpIpfEvtDetailStr }
     DESCRIPTION
        "Invalid or unsupported TPM detected in the system. TPM is disabled.
Data filed unused"

     --#SUMMARY "Invalid or unsupported TPM detected in the system. TPM is disabled."
     --#ARGUMENTS {}
     --#SEVERITY WARNING
     --#TIMEINDEX 100
     --#STATE OPERATIONAL
::= 12048


hpevtTPMFailInit TRAP-TYPE
     ENTERPRISE hpIpfE0Events
     VARIABLES { hpIpfEvtDetailStr }
     DESCRIPTION
        "Firmware cannot initialize the TPM. TPM related security feature are disabled
Data field unused"

     --#SUMMARY "TPM failed initialization. Security features disabled."
     --#ARGUMENTS {}
     --#SEVERITY WARNING
     --#TIMEINDEX 100
     --#STATE OPERATIONAL
::= 12049


hpevtCpuTempExceedHiThres TRAP-TYPE
     ENTERPRISE hpIpfE0Events
     VARIABLES { hpIpfEvtDetailStr }
     DESCRIPTION
        "A CPU module's temperature has exceed the high temperature threshold or a CPU power module fault has occured. As a result of this event, the CPU has been inhibited. The Cell must be powered off then on using the MP's PE command before the CPU module will be powered again."

     --#SUMMARY "A CPU module's temperature has exceed the high temperature threshold or a CPU power module fault has occured. As a result of this event, the CPU has been inhibited. The Cell must be powered off then on using the MP's PE command to clear."
     --#ARGUMENTS {}
     --#SEVERITY CRITICAL
     --#TIMEINDEX 100
     --#STATE OPERATIONAL
::= 12050


hpevtSFWDetErrStablStorFlsh TRAP-TYPE
     ENTERPRISE hpIpfE0Events
     VARIABLES { hpIpfEvtDetailStr }
     DESCRIPTION
        "An error occurred while writing to stable store flash.  Data field is unused."

     --#SUMMARY "SFW detected an error while writing to stable store flash."
     --#ARGUMENTS {}
     --#SEVERITY WARNING
     --#TIMEINDEX 100
     --#STATE OPERATIONAL
::= 12069


hpevtInlckOpenPCIPwr TRAP-TYPE
     ENTERPRISE hpIpfE0Events
     VARIABLES { hpIpfEvtDetailStr }
     DESCRIPTION
        "PCI interlock has been opened with PCI slot power on.  The datafield can be decoded as follows (where byte 0 is the rightmost byte):
byte offset 2:PCI slot number
byte offset 5: IO Chassis number
byte offset 6: IO Bay number
byte offset 7: Cabinet number
"

     --#SUMMARY "PCI interlock open with PCI power applied."
     --#ARGUMENTS {}
     --#SEVERITY WARNING
     --#TIMEINDEX 100
     --#STATE OPERATIONAL
::= 12091


hpevtFaltDetDropRegIO TRAP-TYPE
     ENTERPRISE hpIpfE0Events
     VARIABLES { hpIpfEvtDetailStr }
     DESCRIPTION
        "The specified low dropout regulator on the IO backplane is reporting a fault.  The specified power rail is reporting a fault.  The number in the slot field of 
the physical location is the rail number that caused the fault.  Rails are:  4 = LDO 2.5v for Esca 0, 5 = LDO 2.5v for Esca 1, 1.5v, 7 = Other backplane 2.5v, 8 = Other backplane 1.2v"

     --#SUMMARY "Fault detected on low drop out regulator on I/O backplane."
     --#ARGUMENTS {}
     --#SEVERITY CRITICAL
     --#TIMEINDEX 100
     --#STATE OPERATIONAL
::= 12101


hpevtFaltDetDropRegManBckPlne TRAP-TYPE
     ENTERPRISE hpIpfE0Events
     VARIABLES { hpIpfEvtDetailStr }
     DESCRIPTION
        "The specified low dropout regulator on the main backplane is reporting a fault.  The number in the slot field of 
the physical location is the rail number that caused the fault.  Rails are:  0 = SysBP xb0 1.5v, 1 = SysBp xb1 1.5v, 2 = SysBp switched 3.3v, 3 = SysBp LDO xb0 2.5v, 4 = SysBp xb1 LDO 2.5v, 5 = SysBp LDO 1.5v br0, 6 = SysBp LDO 1.5v br1"

     --#SUMMARY "Fault detected on low drop out regulator on main backplane."
     --#ARGUMENTS {}
     --#SEVERITY CRITICAL
     --#TIMEINDEX 100
     --#STATE OPERATIONAL
::= 12102


hpevtFaltDetHotswpCoreIO TRAP-TYPE
     ENTERPRISE hpIpfE0Events
     VARIABLES { hpIpfEvtDetailStr }
     DESCRIPTION
        "The hot swap controller for the specified core IO is reporting fault."

     --#SUMMARY "Fault detected hot swap controller of specified core IO."
     --#ARGUMENTS {}
     --#SEVERITY CRITICAL
     --#TIMEINDEX 100
     --#STATE OPERATIONAL
::= 12103


hpevtErrRetrvCrssbarChipNmbr TRAP-TYPE
     ENTERPRISE hpIpfE0Events
     VARIABLES { hpIpfEvtDetailStr }
     DESCRIPTION
        "An error occurred while retrieving the crossbar chip number.  Data Field: cell number << 56 | port number << 44 | return status"

     --#SUMMARY "An error occurred while retrieving the crossbar chip number."
     --#ARGUMENTS {}
     --#SEVERITY WARNING
     --#TIMEINDEX 100
     --#STATE OPERATIONAL
::= 12109


hpevtCellNotCfgCLMMode TRAP-TYPE
     ENTERPRISE hpIpfE0Events
     VARIABLES { hpIpfEvtDetailStr }
     DESCRIPTION
        "For most workloads, the system performance may be degraded if CLM mode is not enabled for all of the cells in a partition.  Windows Server 2003 contains additional support to optimize for CLM systems, increasing the performance compared to an interleaved configuration.
"

     --#SUMMARY "One or more of the cells are not configured for Cell-Local Memory (CLM) mode"
     --#ARGUMENTS {}
     --#SEVERITY WARNING
     --#TIMEINDEX 100
     --#STATE OPERATIONAL
::= 12119


hpevttDoblDramInvoke TRAP-TYPE
     ENTERPRISE hpIpfE0Events
     VARIABLES { hpIpfEvtDetailStr }
     DESCRIPTION
        "Corrected memory errors have been detected. Double DRAM chip sparing events have been invoked."

     --#SUMMARY "Double DRAM chip sparing events have been invoked."
     --#ARGUMENTS {}
     --#SEVERITY WARNING
     --#TIMEINDEX 100
     --#STATE OPERATIONAL
::= 12120


hpevtErrCrssbarCrctByHW TRAP-TYPE
     ENTERPRISE hpIpfE0Events
     VARIABLES { hpIpfEvtDetailStr }
     DESCRIPTION
        "A error occurred in the crossbar controller and was corrected by the hardware."

     --#SUMMARY "A platform error was detected by the firmware/hardware, and corrected by using a spare channel."
     --#ARGUMENTS {}
     --#SEVERITY WARNING
     --#TIMEINDEX 100
     --#STATE OPERATIONAL
::= 12121


hpevtErrCrssChipBckPln TRAP-TYPE
     ENTERPRISE hpIpfE0Events
     VARIABLES { hpIpfEvtDetailStr }
     DESCRIPTION
        "A platform error was detected by the firmware/hardware, and corrected by using a spare channel.  The error occurred between the crossbar chips on the backplane(s)."

     --#SUMMARY "A platform error was detected by the firmware/hardware, and corrected by using a spare channel."
     --#ARGUMENTS {}
     --#SEVERITY WARNING
     --#TIMEINDEX 100
     --#STATE OPERATIONAL
::= 12127


hpevtErrCeLLIO TRAP-TYPE
     ENTERPRISE hpIpfE0Events
     VARIABLES { hpIpfEvtDetailStr }
     DESCRIPTION
        "A platform error was detected by the firmware/hardware, and corrected by using a spare channel.  The error occurred between the cell controller and the IO controller."

     --#SUMMARY "A platform error was detected by the firmware/hardware, and corrected by using a spare channel."
     --#ARGUMENTS {}
     --#SEVERITY WARNING
     --#TIMEINDEX 100
     --#STATE OPERATIONAL
::= 12128


hpevtMltPltFrmErrCellBckPln TRAP-TYPE
     ENTERPRISE hpIpfE0Events
     VARIABLES { hpIpfEvtDetailStr }
     DESCRIPTION
        "Multiple platform errors were detected and corrected by the firmware/hardware.   The errors occurred between the cell controller and the backplane."

     --#SUMMARY "Multiple platform errors were detected and corrected by the firmware/hardware."
     --#ARGUMENTS {}
     --#SEVERITY WARNING
     --#TIMEINDEX 100
     --#STATE OPERATIONAL
::= 12129


hpevtMultPltFrmErrCrssChpBckPln TRAP-TYPE
     ENTERPRISE hpIpfE0Events
     VARIABLES { hpIpfEvtDetailStr }
     DESCRIPTION
        "Multiple platform errors were detected and corrected by the firmware/hardware.  The errors occurred between the crossbar chips on the backplane(s)."

     --#SUMMARY "Multiple platform errors were detected and corrected by the firmware/hardware."
     --#ARGUMENTS {}
     --#SEVERITY WARNING
     --#TIMEINDEX 100
     --#STATE OPERATIONAL
::= 12130


hpevtMultPltFrmErrCeLLIO TRAP-TYPE
     ENTERPRISE hpIpfE0Events
     VARIABLES { hpIpfEvtDetailStr }
     DESCRIPTION
        "Multiple platform errors were detected and corrected by the firmware/hardware.   The errors occurred between the cell controller and the IO controller."

     --#SUMMARY "Multiple platform errors were detected and corrected by the firmware/hardware."
     --#ARGUMENTS {}
     --#SEVERITY WARNING
     --#TIMEINDEX 100
     --#STATE OPERATIONAL
::= 12131


hpevtServIDNotMatchCab TRAP-TYPE
     ENTERPRISE hpIpfE0Events
     VARIABLES { hpIpfEvtDetailStr }
     DESCRIPTION
        "The server identification information does not match the cabinet type. The server will not power on until this condition is resolved."

     --#SUMMARY "The server ID does not match the cabinet type."
     --#ARGUMENTS {}
     --#SEVERITY CRITICAL
     --#TIMEINDEX 100
     --#STATE OPERATIONAL
::= 12132


hpevtDupDimNumDetect TRAP-TYPE
     ENTERPRISE hpIpfE0Events
     VARIABLES { hpIpfEvtDetailStr }
     DESCRIPTION
        "Duplicate DIMM serial numbers have been detected.  Data field gives physical location of DIMM.  Check for other events specifying other DIMMs with same serial number."

     --#SUMMARY "Duplicate DIMM serial numbers have been detected.  Data field gives physical location of DIMM.  Check for other events specifying other DIMMs with same serial number."
     --#ARGUMENTS {}
     --#SEVERITY WARNING
     --#TIMEINDEX 100
     --#STATE OPERATIONAL
::= 12135


hpevtMPLostUPS TRAP-TYPE
     ENTERPRISE hpIpfE0Events
     VARIABLES { hpIpfEvtDetailStr }
     DESCRIPTION
        "The MP has lost communications with the UPS via SNMP over the LAN"

     --#SUMMARY "The MP has lost lan communication with the UPS."
     --#ARGUMENTS {}
     --#SEVERITY WARNING
     --#TIMEINDEX 100
     --#STATE OPERATIONAL
::= 12143


hpevtMPGainLanCommUPS TRAP-TYPE
     ENTERPRISE hpIpfE0Events
     VARIABLES { hpIpfEvtDetailStr }
     DESCRIPTION
        "The MP lan communications with the UPS have been restored."

     --#SUMMARY "The MP has re-gained lan communication with the UPS."
     --#ARGUMENTS {}
     --#SEVERITY WARNING
     --#TIMEINDEX 100
     --#STATE OPERATIONAL
::= 12144


hpevtUnrecovProcIFAinterptInFW TRAP-TYPE
     ENTERPRISE hpIpfE0Events
     VARIABLES { hpIpfEvtDetailStr }
     DESCRIPTION
        "An unrecoverrable processor interrupt occured while in IPF firmware. The data value is the processor IFA."

     --#SUMMARY "An unrecoverrable processor interrupt occured while in IPF firmware. The data value is the processor IFA."
     --#ARGUMENTS {}
     --#SEVERITY CRITICAL
     --#TIMEINDEX 100
     --#STATE OPERATIONAL
::= 12149


hpevtUnrecovProcISRinterptInFW TRAP-TYPE
     ENTERPRISE hpIpfE0Events
     VARIABLES { hpIpfEvtDetailStr }
     DESCRIPTION
        "An unrecoverable processor interrupt occured while in IPF firmware. The event data is the processor ISR."

     --#SUMMARY "An unrecoverable processor interrupt occured while in IPF firmware. The event data is the processor ISR."
     --#ARGUMENTS {}
     --#SEVERITY CRITICAL
     --#TIMEINDEX 100
     --#STATE OPERATIONAL
::= 12150


hpevtDblChipSpareInvoked TRAP-TYPE
     ENTERPRISE hpIpfE0Events
     VARIABLES { hpIpfEvtDetailStr }
     DESCRIPTION
        "System firmware has detected and corrected memory errors. Double chip sparing has been invoked to help mitigate this condition."

     --#SUMMARY "Double chip sparing has been invoked"
     --#ARGUMENTS {}
     --#SEVERITY WARNING
     --#TIMEINDEX 100
     --#STATE OPERATIONAL
::= 12153


hpevtExtClkCablRemvFrmCPUCab TRAP-TYPE
     ENTERPRISE hpIpfE0Events
     VARIABLES { hpIpfEvtDetailStr }
     DESCRIPTION
        "External clock cable has been removed from the CPU cabinet. The data field contains the physical location of the cabinet."

     --#SUMMARY "External clock cable has been removed from the CPU cabinet. The data field contains the physical location of the cabinet."
     --#ARGUMENTS {}
     --#SEVERITY CRITICAL
     --#TIMEINDEX 100
     --#STATE OPERATIONAL
::= 12155


hpevtSysFabEncntLnkErr TRAP-TYPE
     ENTERPRISE hpIpfE0Events
     VARIABLES { hpIpfEvtDetailStr }
     DESCRIPTION
        "System Fabric encountered a link error after opening up the fabric link"

     --#SUMMARY "System Fabric encountered a link error after opening up the fabric link."
     --#ARGUMENTS {}
     --#SEVERITY WARNING
     --#TIMEINDEX 100
     --#STATE OPERATIONAL
::= 12156


hpevtFatErrOnCelToFabPrt44I32I1 TRAP-TYPE
     ENTERPRISE hpIpfE0Events
     VARIABLES { hpIpfEvtDetailStr }
     DESCRIPTION
        "Fatal errors are present on a cell's link to the fabric.  Data Field: (crossbar port << 44) | (crossbar << 32) | 1"

     --#SUMMARY "Fatal errors are present on a cell's link to the fabric.  Data Field: (crossbar port  44) | (crossbar  32) | 1"
     --#ARGUMENTS {}
     --#SEVERITY WARNING
     --#TIMEINDEX 100
     --#STATE OPERATIONAL
::= 12157


hpevtSysFWgetFabProblm TRAP-TYPE
     ENTERPRISE hpIpfE0Events
     VARIABLES { hpIpfEvtDetailStr }
     DESCRIPTION
        "System firmware encountered fabric problems.  Data Field: (crossbar port << 44) | (crossbar << 32)"

     --#SUMMARY "System firmware encountered fabric problems.  Data Field: (crossbar port  44) | (crossbar  32)"
     --#ARGUMENTS {}
     --#SEVERITY WARNING
     --#TIMEINDEX 100
     --#STATE OPERATIONAL
::= 12159


hpevtFatErrCelLnkToFabPrt44I32 TRAP-TYPE
     ENTERPRISE hpIpfE0Events
     VARIABLES { hpIpfEvtDetailStr }
     DESCRIPTION
        "Fatal errors are present on a cell's link to the fabric.  Data Field: (crossbar port << 44) | (crossbar << 32)"

     --#SUMMARY "Fatal errors are present on a cell's link to the fabric.  Data Field: (crossbar port  44) | (crossbar  32)"
     --#ARGUMENTS {}
     --#SEVERITY WARNING
     --#TIMEINDEX 100
     --#STATE OPERATIONAL
::= 12160


hpevtSysOSRecovFrmPCIErrL1 TRAP-TYPE
     ENTERPRISE hpIpfE0Events
     VARIABLES { hpIpfEvtDetailStr }
     DESCRIPTION
        "A PCI error occurred, but the OS recovered."

     --#SUMMARY "The operating system has recovered from a PCI error."
     --#ARGUMENTS {}
     --#SEVERITY WARNING
     --#TIMEINDEX 100
     --#STATE OPERATIONAL
::= 12161


hpevtSysOSRecovFrmPCIErrL2 TRAP-TYPE
     ENTERPRISE hpIpfE0Events
     VARIABLES { hpIpfEvtDetailStr }
     DESCRIPTION
        "A PCI error occurred, but the operating system recovered."

     --#SUMMARY "The operating system has recovered from a PCI error."
     --#ARGUMENTS {}
     --#SEVERITY WARNING
     --#TIMEINDEX 100
     --#STATE OPERATIONAL
::= 12162


hpevtSysOSRecovFrmPCIErrL5 TRAP-TYPE
     ENTERPRISE hpIpfE0Events
     VARIABLES { hpIpfEvtDetailStr }
     DESCRIPTION
        "A PCI error occurred, but the operating system recovered"

     --#SUMMARY "The operating system has recovered from a PCI error."
     --#ARGUMENTS {}
     --#SEVERITY WARNING
     --#TIMEINDEX 100
     --#STATE OPERATIONAL
::= 12163


hpevtReqPwrOnDenied TRAP-TYPE
     ENTERPRISE hpIpfE0Events
     VARIABLES { hpIpfEvtDetailStr }
     DESCRIPTION
        "The request to power on, either via MP user interface, power button, or other, was denied by the Enclosure Manager."

     --#SUMMARY "The request to power on, either via MP user interface, power button, or other, was denied by the Enclosure Manager."
     --#ARGUMENTS {}
     --#SEVERITY CRITICAL
     --#TIMEINDEX 100
     --#STATE OPERATIONAL
::= 12164


hpevtBladeFrcPWon TRAP-TYPE
     ENTERPRISE hpIpfE0Events
     VARIABLES { hpIpfEvtDetailStr }
     DESCRIPTION
        "The blade has been forced to power-on, either via the MP user interface or the power button.  The blade did not negotiate with the enclosure to insure that there was sufficient power for this action."

     --#SUMMARY "The blade has been forced to power-on, either via the MP user interface or the power button.  The blade did not negotiate with the enclosure to insure that there was sufficient power for this action."
     --#ARGUMENTS {}
     --#SEVERITY WARNING
     --#TIMEINDEX 100
     --#STATE OPERATIONAL
::= 12165


hpevtMPNotRecvRespEnclMangr TRAP-TYPE
     ENTERPRISE hpIpfE0Events
     VARIABLES { hpIpfEvtDetailStr }
     DESCRIPTION
        "The MP has repeatedly tried to communicate with the enclosure manager and has not received any response"

     --#SUMMARY "The MP has repeatedly tried to communicate with the enclosure manager and has not received any response."
     --#ARGUMENTS {}
     --#SEVERITY WARNING
     --#TIMEINDEX 100
     --#STATE OPERATIONAL
::= 12168


hpevtIntrnlSwErr7193 TRAP-TYPE
     ENTERPRISE hpIpfE0Events
     VARIABLES { hpIpfEvtDetailStr }
     DESCRIPTION
        "This is an internal SW error"

     --#SUMMARY "This is an internal SW error. See Cause/Action ."
     --#ARGUMENTS {}
     --#SEVERITY CRITICAL
     --#TIMEINDEX 100
     --#STATE OPERATIONAL
::= 12193


hpevtIntrnlSwErr7194 TRAP-TYPE
     ENTERPRISE hpIpfE0Events
     VARIABLES { hpIpfEvtDetailStr }
     DESCRIPTION
        "This is an internal SFW error"

     --#SUMMARY "This is an internal SW error. See Cause/Action."
     --#ARGUMENTS {}
     --#SEVERITY CRITICAL
     --#TIMEINDEX 100
     --#STATE OPERATIONAL
::= 12194


hpevtIntrnlSwErr7195 TRAP-TYPE
     ENTERPRISE hpIpfE0Events
     VARIABLES { hpIpfEvtDetailStr }
     DESCRIPTION
        "This is an internal SFW error"

     --#SUMMARY "This is an internal SW error. See Cause/Action."
     --#ARGUMENTS {}
     --#SEVERITY CRITICAL
     --#TIMEINDEX 100
     --#STATE OPERATIONAL
::= 12195


hpevtIntrnlSwErr7196 TRAP-TYPE
     ENTERPRISE hpIpfE0Events
     VARIABLES { hpIpfEvtDetailStr }
     DESCRIPTION
        "This is an internal SFW error"

     --#SUMMARY "This is an internal SW error. See Cause/Action."
     --#ARGUMENTS {}
     --#SEVERITY CRITICAL
     --#TIMEINDEX 100
     --#STATE OPERATIONAL
::= 12196


hpevtComplxProfNoMtch TRAP-TYPE
     ENTERPRISE hpIpfE0Events
     VARIABLES { hpIpfEvtDetailStr }
     DESCRIPTION
        "There are miscompares in the complex profiles between cells in a partition.  Data field is unused, earlier events will give more detail."

     --#SUMMARY "The complex profiles between cells in a partition do not match. Data field is unused, earlier events will give more detail."
     --#ARGUMENTS {}
     --#SEVERITY CRITICAL
     --#TIMEINDEX 100
     --#STATE OPERATIONAL
::= 12199


hpevtIODevMissCore TRAP-TYPE
     ENTERPRISE hpIpfE0Events
     VARIABLES { hpIpfEvtDetailStr }
     DESCRIPTION
        "An I/O device is missing from the Core I/O. Internal peripherals may be not accessible."

     --#SUMMARY "An I/O device is missing from the Core I/O"
     --#ARGUMENTS {}
     --#SEVERITY WARNING
     --#TIMEINDEX 100
     --#STATE OPERATIONAL
::= 12204


hpevtFparUnablNotiCPU TRAP-TYPE
     ENTERPRISE hpIpfE0Events
     VARIABLES { hpIpfEvtDetailStr }
     DESCRIPTION
        "An fPar's GPE_EN bits are not set up to handle receiving a CPU migrate.  This event is emitted 2 times, the Data field is different each time.
1. Data field: Address of GPE block
2. Data field: bits 31:0 Virtual GPE_EN register (lower byte)
                     bits 63:32 Enable bits needed for successful migrate"

     --#SUMMARY "fPars PMI handler was unable to Notify a CPU's new owner after a migrate."
     --#ARGUMENTS {}
     --#SEVERITY WARNING
     --#TIMEINDEX 100
     --#STATE OPERATIONAL
::= 12207


hpevtFparUnablNotiCpuIOSAPICredir TRAP-TYPE
     ENTERPRISE hpIpfE0Events
     VARIABLES { hpIpfEvtDetailStr }
     DESCRIPTION
        "FSHWA was unable to notify the new owner of a CPU migrate.  This event is emitted 2 times:
1. Data field: IOSAPIC Address
2. Data field: Virtual IOSAPIC SCI redir"

     --#SUMMARY "fPars PMI handler was unable to Notify a CPU's new owner after a migrate."
     --#ARGUMENTS {}
     --#SEVERITY WARNING
     --#TIMEINDEX 100
     --#STATE OPERATIONAL
::= 12208


hpevtOSSetWtchDogTimerToTimeOut TRAP-TYPE
     ENTERPRISE hpIpfE0Events
     VARIABLES { hpIpfEvtDetailStr }
     DESCRIPTION
        "The operating system set the watchdog timer to time out if it was not reset within a specified time.  It was not reset and has timed out. The management processor will now take the action specified when the timer was set."

     --#SUMMARY "The operating system set the watchdog timer to time out if it was not reset within a specified time.  It was not reset and has timed out. The management processor will now take the action specified when the timer was set."
     --#ARGUMENTS {}
     --#SEVERITY WARNING
     --#TIMEINDEX 100
     --#STATE OPERATIONAL
::= 12210


hpevtOSShtDwnDueMCA TRAP-TYPE
     ENTERPRISE hpIpfE0Events
     VARIABLES { hpIpfEvtDetailStr }
     DESCRIPTION
        "An OS is shutting down due to an MCA (Machine Check Abort) or INIT."

     --#SUMMARY "An OS is shutting down due to an MCA (Machine Check Abort) or INIT."
     --#ARGUMENTS {}
     --#SEVERITY CRITICAL
     --#TIMEINDEX 100
     --#STATE OPERATIONAL
::= 12217


hpevtOSShtDwnDuePanic TRAP-TYPE
     ENTERPRISE hpIpfE0Events
     VARIABLES { hpIpfEvtDetailStr }
     DESCRIPTION
        "An OS is shutting down due to a panic."

     --#SUMMARY "An OS is shutting down due to a panic."
     --#ARGUMENTS {}
     --#SEVERITY CRITICAL
     --#TIMEINDEX 100
     --#STATE OPERATIONAL
::= 12218


hpevtCLUFWIncomptblSysType TRAP-TYPE
     ENTERPRISE hpIpfE0Events
     VARIABLES { hpIpfEvtDetailStr }
     DESCRIPTION
        "Following an in-the-box system type upgrade, or after a UGUY board was replaced, the CLU FW may not have been updated to an appropriate revision for the system type."

     --#SUMMARY "An instance of CLU FW has an installed firmware revision that is incompatible with the system type. Many system operations will fail until this condition is resolved."
     --#ARGUMENTS {}
     --#SEVERITY CRITICAL
     --#TIMEINDEX 100
     --#STATE OPERATIONAL
::= 1222


hpevtOnlnIdentHWProb TRAP-TYPE
     ENTERPRISE hpIpfE0Events
     VARIABLES { hpIpfEvtDetailStr }
     DESCRIPTION
        "Diagnostics running under the OS have detected a problem with the identified hardware."

     --#SUMMARY "The online diagnostics have identified a hardware problem."
     --#ARGUMENTS {}
     --#SEVERITY CRITICAL
     --#TIMEINDEX 100
     --#STATE OPERATIONAL
::= 12227


hpevtProcOvTemp TRAP-TYPE
     ENTERPRISE hpIpfE0Events
     VARIABLES { hpIpfEvtDetailStr }
     DESCRIPTION
        "The processor temperature has exceeded normal limits. HP's Enhanced Thermal Management (ETM) feature has been employed to cool the processor. If the temperature problem persists, this will have an adverse impact on the performance of this processor.
"

     --#SUMMARY "Over-Temperature or power condition detected for processor"
     --#ARGUMENTS {}
     --#SEVERITY WARNING
     --#TIMEINDEX 100
     --#STATE OPERATIONAL
::= 12228


hpevtErrChkFabBootStat TRAP-TYPE
     ENTERPRISE hpIpfE0Events
     VARIABLES { hpIpfEvtDetailStr }
     DESCRIPTION
        "An error occurred while checking the fabricless boot state"

     --#SUMMARY "An error occurred while checking the fabricless boot state"
     --#ARGUMENTS {}
     --#SEVERITY WARNING
     --#TIMEINDEX 100
     --#STATE OPERATIONAL
::= 12229


hpevtSysFwUnblClrLnkErrMsk TRAP-TYPE
     ENTERPRISE hpIpfE0Events
     VARIABLES { hpIpfEvtDetailStr }
     DESCRIPTION
        "System firmware was unable to clear the link error masks"

     --#SUMMARY "System firmware was unable to clear the link error masks"
     --#ARGUMENTS {}
     --#SEVERITY WARNING
     --#TIMEINDEX 100
     --#STATE OPERATIONAL
::= 12230


hpevtSysFwNotDetLnkAdrr TRAP-TYPE
     ENTERPRISE hpIpfE0Events
     VARIABLES { hpIpfEvtDetailStr }
     DESCRIPTION
        "System firmware could not determine a link's address"

     --#SUMMARY "System firmware could not determine a link's address"
     --#ARGUMENTS {}
     --#SEVERITY WARNING
     --#TIMEINDEX 100
     --#STATE OPERATIONAL
::= 12231


hpevtSysFwUnblTurnBadLnkOff TRAP-TYPE
     ENTERPRISE hpIpfE0Events
     VARIABLES { hpIpfEvtDetailStr }
     DESCRIPTION
        "System firmware was unable to turn a bad link off"

     --#SUMMARY "System firmware was unable to turn a bad link off"
     --#ARGUMENTS {}
     --#SEVERITY WARNING
     --#TIMEINDEX 100
     --#STATE OPERATIONAL
::= 12232


hpevtWindWtchDogXpired TRAP-TYPE
     ENTERPRISE hpIpfE0Events
     VARIABLES { hpIpfEvtDetailStr }
     DESCRIPTION
        "The Wiindows watchdog timer has expired.  The nPartition will either be reset or powered off.
The data field contains the following information:
byte 2 - cell slot number of the cell that generated the timeout event
byte 3 - nPartition number (SX2000 superdome only)
byte 4 - timeout action (0 = Reset, 1 = Power off)
byte 7 - cabinet number

"

     --#SUMMARY "The windows watchdog timer has expired.  The partition associated with the cell with the expired timer will be reset."
     --#ARGUMENTS {}
     --#SEVERITY CRITICAL
     --#TIMEINDEX 100
     --#STATE OPERATIONAL
::= 12244


hpevtMPCtrlReprtMPBusCommFail TRAP-TYPE
     ENTERPRISE hpIpfE0Events
     VARIABLES { hpIpfEvtDetailStr }
     DESCRIPTION
        "An MP Bus communications device is reporting a hardware revision that is known to cause MP Bus communications failures. The value in the data field indicates the physical location of the PM, CLU, or PDHC device that is failing."

     --#SUMMARY "An entity's MP Bus communications controller is reporting a hardware revision that is known to cause MP Bus communications failures."
     --#ARGUMENTS {}
     --#SEVERITY CRITICAL
     --#TIMEINDEX 100
     --#STATE OPERATIONAL
::= 12251


hpevt12VPCIFailonIOChass TRAP-TYPE
     ENTERPRISE hpIpfE0Events
     VARIABLES { hpIpfEvtDetailStr }
     DESCRIPTION
        "Main power at the PCI slot located on the IO Chassis has faulted."

     --#SUMMARY "12v power to a PCI slot located on the IO Chassis has power faulted."
     --#ARGUMENTS {}
     --#SEVERITY CRITICAL
     --#TIMEINDEX 100
     --#STATE OPERATIONAL
::= 12255


hpevtSFWDetFailOptmzFab TRAP-TYPE
     ENTERPRISE hpIpfE0Events
     VARIABLES { hpIpfEvtDetailStr }
     DESCRIPTION
        "A failure was encountered while running the Fabric API to optimize the fabric."

     --#SUMMARY "SFW detected a failure while optimizing the fabric."
     --#ARGUMENTS {}
     --#SEVERITY WARNING
     --#TIMEINDEX 100
     --#STATE OPERATIONAL
::= 12289


hpevtCritFailCellOnline TRAP-TYPE
     ENTERPRISE hpIpfE0Events
     VARIABLES { hpIpfEvtDetailStr }
     DESCRIPTION
        "A critical failure occured during a cell online add or delete call."

     --#SUMMARY "A critical failure occured during a cell online add or delete."
     --#ARGUMENTS {}
     --#SEVERITY CRITICAL
     --#TIMEINDEX 100
     --#STATE OPERATIONAL
::= 12291


hpevtCellHasIncomptbleHwFW TRAP-TYPE
     ENTERPRISE hpIpfE0Events
     VARIABLES { hpIpfEvtDetailStr }
     DESCRIPTION
        "A cell being added is not compatible with the partition."

     --#SUMMARY "The cell being added has incompatible hardware or firmware revision with the partition."
     --#ARGUMENTS {}
     --#SEVERITY WARNING
     --#TIMEINDEX 100
     --#STATE OPERATIONAL
::= 12296


hpevtCellFWnotMatchPartFW TRAP-TYPE
     ENTERPRISE hpIpfE0Events
     VARIABLES { hpIpfEvtDetailStr }
     DESCRIPTION
        "The Firmware revision of the cell being added is different from the nPar."

     --#SUMMARY "The System Firmware revision on the cell being added does not match the partition firmware revision."
     --#ARGUMENTS {}
     --#SEVERITY WARNING
     --#TIMEINDEX 100
     --#STATE OPERATIONAL
::= 12297


hpevtBadCellBrdOrBadProcBrd TRAP-TYPE
     ENTERPRISE hpIpfE0Events
     VARIABLES { hpIpfEvtDetailStr }
     DESCRIPTION
        "Bad cell board (on cellular system), or bad processor board (on non-cellular system)."

     --#SUMMARY "Bad cell board (on cellular system), or bad processor board (on non-cellular system)."
     --#ARGUMENTS {}
     --#SEVERITY WARNING
     --#TIMEINDEX 100
     --#STATE OPERATIONAL
::= 12324


hpevtCPUDegradErrThirdCache TRAP-TYPE
     ENTERPRISE hpIpfE0Events
     VARIABLES { hpIpfEvtDetailStr }
     DESCRIPTION
        "CPU performance degraded due to excessive errors in third level cache."

     --#SUMMARY "CPU performance degraded due to excessive errors in third level cache"
     --#ARGUMENTS {}
     --#SEVERITY WARNING
     --#TIMEINDEX 100
     --#STATE OPERATIONAL
::= 12343


hpevtROMFailAuthentc TRAP-TYPE
     ENTERPRISE hpIpfE0Events
     VARIABLES { hpIpfEvtDetailStr }
     DESCRIPTION
        "The alternate ROM failed to authenticate. The current (primary) ROM will continue to be used"

     --#SUMMARY "The alternate ROM failed to authenticate. The current (primary) ROM will continue to be used"
     --#ARGUMENTS {}
     --#SEVERITY CRITICAL
     --#TIMEINDEX 100
     --#STATE OPERATIONAL
::= 12352


hpevtAltrntROMUnblSwap TRAP-TYPE
     ENTERPRISE hpIpfE0Events
     VARIABLES { hpIpfEvtDetailStr }
     DESCRIPTION
        "The alternate ROM was successfully authenticated but the primary and alternate ROM could not be swapped. The current primary will still be used"

     --#SUMMARY "The alternate ROM was successfully authenticated but the primary and alternate ROM could not be swapped. The current primary will still be used."
     --#ARGUMENTS {}
     --#SEVERITY CRITICAL
     --#TIMEINDEX 100
     --#STATE OPERATIONAL
::= 12354




END
