-- COPYRIGHT NOTICE
-- Copyright (c) Hewlett Packard Company, 2003 
-- All rights reserved
-- 
-- 
-- HISTORY
-- $Log: bladetype4-trap.mib,v $
-- Revision 1.1  2006/08/17 21:34:54  kallio
-- New mibs from Mgmt CD 7.60
--
-- Revision 1.1  2006/05/30 15:15:50  kallio
-- Initial revision
-- Revision submit_cheetah_20268/1 2006/04/28 23:37:53 bshao
-- Fixed Angus build issue.
-- 
-- Revision submit_cheetah_20254/1 2006/04/28 13:28:40 vrincian
-- removed
-- 1. bt2SwCubeInserted 
-- 2. bt2SwCubeRemoved 
-- 
-- inserted
-- 1. bt2SwTempExceedThreshold
-- 2. bt2SwTempReturnThreshold
-- 
-- Revision submit_cheetah_20248/1 2006/04/28 12:58:59 vrincian
-- Lucian Badescu: rename all bt2traps and their ENTERPRISE OID.
-- Their new names will be bt4* traps and the ENTERPRISE OID bt4Traps.
-- 
-- Revision submit_cheetah_20001/1 2006/04/19 09:14:28 vrincian
-- Lucian Badescu: Change SNMP mib file title depending on project type.
-- Complete the support for Angus's private mibs beneath
-- hpSwitchModuleBladetype4-Mgmt OID.
-- 
-- Revision submit_cheetah_19282/1 2006/03/24 10:25:35 vrincian
-- Removed bt2SwPrimaryPowerSupplyFailure, bt2SwTempExceedThreshold,
-- bt2SwRackLocationChange, bt2SwTempReturnThreshold, 
-- bt2SwFanFailure and bt2SwFanFailureFixed traps from Angus project
-- 
-- Revision submit_cheetah_19130/1 2006/03/22 10:51:22 vrincian
-- Lucian Badescu: fix for 6862  - "need unique sysObjectID for Angus" and
-- 6863 - "Need to update hpswitchpl.mib".
-- Put all Angus private OIDs beneath hpSwitchModuleBladetype4-Mgmt.
-- 
-- Revision submit_cheetah_17624/1 2006/02/01 16:16:40 vrincian
-- Remove VRRP feature for Angus.
-- 
-- Revision submit_cheetah_14270/1 2005/09/14 16:37:36 coman
-- Traps for Cub removed/inserted added
-- 
-- Revision submit_cheetah_13551/1 2005/08/05 17:26:49 coman
-- UFD implementation ported from 2.2 stream
-- 
-- Revision submit_cheetah_10393/1 2005/01/05 21:01:43 mmacnt
-- code reorg - moved from lib/agent
-- 
-- Revision submit_cheetah_8578/1 2004/07/30 00:52:53 rrekha
-- Moved from /src/bert/lib/agent directory.
-- 
-- Revision submit_zoe_500/1 2003/07/07 23:50:57 tolin
-- Fixes Defect #702393: Add Severity level for Bert generated traps. 
-- 
-- Revision submit_zoe_496/1 2003/07/07 23:10:16 tolin
-- Fixes Defect #706213: Correctly use the name bt2SwFanFailureFixed as 
-- the trap description name.
-- 
-- Revision submit_zoe_464/1 2003/06/23 23:40:36 smiao
-- Fixed Q00695674. Dispalyed trap OID correctly.
-- 
-- Revision submit_zoe_442/1 2003/06/13 03:14:45 tolin
-- Fixes Defect #650736: Correct the description of Rack Location change trap
-- description to reference rac-loc instead of DefGwUp
-- 
-- Revision submit_zoe_428/1 2003/06/10 18:05:49 smiao
-- Fixed the compiler error.
-- 
-- Revision submit_zoe_427/1 2003/06/09 23:59:55 smiao
-- Checked in for enviromental trap definitions.
-- 
-- Revision submit_zoe_423/1 2003/06/06 21:06:27 smiao
-- Fixed Q00673523. Added trap and syslog for firmware download.
-- 
-- Revision submit_zoe_419/1 2003/06/05 22:35:42 smiao
-- Fixed Q00673526. Added traps for configuration changes.
-- 
-- Revision submit_zoe_397/1 2003/05/29 01:12:07 smiao
-- Fixed Q00650736. Put correct description for bt2SwitchRackLoactionChange.
-- 
-- Revision submit_zoe_186/1 2003/02/18 22:22:13 smiao
-- Added rack location change trap.
-- 
-- Revision submit_zoe_181/1 2003/02/14 18:18:00 smiao
-- Adjusted MIB nodes for HP MIB tree.
-- 
-- Revision submit_zoe_165/1 2003/02/04 23:05:49 smiao
-- Created MIB files for HP BERT project.
-- 
-- $EndLog$

BLADETYPE4-TRAP-MIB DEFINITIONS ::= BEGIN

IMPORTS
    TRAP-TYPE
        FROM RFC-1215
    sysName, sysLocation, sysContact, DisplayString
        FROM RFC1213-MIB
    hpSwitchBladeType4-Mgmt
        FROM HP-SWITCH-PL-MIB
    agSlotNumber, agRackId, agChassis
        FROM BLADETYPE4-SWITCH-MIB 
    ipCurCfgGwIndex, ipCurCfgGwAddr 
        FROM BLADETYPE4-NETWORK-MIB;

bt4Traps	OBJECT IDENTIFIER
    ::= { hpSwitchBladeType4-Mgmt 7 }

-- SECTION 2:  Temporary Object Definitions Used In Traps

bt4SwTrapDisplayString OBJECT-TYPE
        SYNTAX  DisplayString (SIZE(0..255))
        ACCESS  read-only
        STATUS  mandatory
        DESCRIPTION
                "Temporary string object used to store information being sent
                 in an Bladetype4 Switch trap."
        ::= { bt4Traps 1000 }

-- SECTION 3:  Trap Definitions


bt4SwDefGwUp TRAP-TYPE
        ENTERPRISE      bt4Traps
        VARIABLES       { ipCurCfgGwIndex,
                          ipCurCfgGwAddr,
                          sysName, sysLocation, sysContact }
        DESCRIPTION
                "A bt4SwDefGwUp trap signifies that the default
                 gateway is alive."

		--#SEVERITY INFORMATIONAL

        ::= 2   -- 0x02

bt4SwDefGwDown TRAP-TYPE
        ENTERPRISE      bt4Traps
        VARIABLES       { ipCurCfgGwIndex,
                          ipCurCfgGwAddr,
                          sysName, sysLocation, sysContact }
        DESCRIPTION
                "A bt4SwDefGwDown trap signifies that the default
                 gateway is down."

		--#SEVERITY INFORMATIONAL

        ::= 3   -- 0x03

bt4SwDefGwInService TRAP-TYPE
        ENTERPRISE      bt4Traps
        VARIABLES       { ipCurCfgGwIndex,
                          ipCurCfgGwAddr,
                          sysName, sysLocation, sysContact }
        DESCRIPTION
                "A bt4SwDefGwEnabled trap signifies that the default
                 gateway is up and in service."

		--#SEVERITY INFORMATIONAL

        ::= 4   -- 0x04

bt4SwDefGwNotInService TRAP-TYPE
        ENTERPRISE      bt4Traps
        VARIABLES       { ipCurCfgGwIndex,
                          ipCurCfgGwAddr,
                          sysName, sysLocation, sysContact }
        DESCRIPTION
                "A bt4SwDefGwDisabled trap signifies that the default
                 gateway is alive but not in service."

		--#SEVERITY INFORMATIONAL

        ::= 5   -- 0x05



bt4SwLoginFailure TRAP-TYPE
        ENTERPRISE      bt4Traps
        VARIABLES       { bt4SwTrapDisplayString,
                          sysName, sysLocation, sysContact }
        DESCRIPTION
                "A bt4SwLoginFailure trap signifies that someone failed to
                 enter a valid username/password combination."
		--#SEVERITY MAJOR

        ::= 19 -- 0x13


bt4SwApplyComplete TRAP-TYPE
        ENTERPRISE      bt4Traps
        VARIABLES       { bt4SwTrapDisplayString,
                          sysName, sysLocation, sysContact }
        DESCRIPTION
                "A bt4SwApplyComplete signifies that new configuration
		 has been applied." 
		--#SEVERITY INFORMATIONAL

        ::= 27 -- 0x1B

bt4SwSaveComplete TRAP-TYPE
        ENTERPRISE      bt4Traps
        VARIABLES       { bt4SwTrapDisplayString,
                          sysName, sysLocation, sysContact }
        DESCRIPTION
                "A bt4SwApplyComplete signifies that new configuration
		 has been saved." 
		--#SEVERITY INFORMATIONAL

        ::= 28 -- 0x1C

bt4SwFwDownloadSucess TRAP-TYPE
        ENTERPRISE      bt4Traps
        VARIABLES       { bt4SwTrapDisplayString,
                          sysName, sysLocation, sysContact }
        DESCRIPTION
                "A bt4SwFwDownloadSuccess signifies that firmware
		 has been downloaded to [image1|image2|boot image]." 
		--#SEVERITY INFORMATIONAL

        ::= 29 -- 0x1D

bt4SwFwDownloadFailure TRAP-TYPE
        ENTERPRISE      bt4Traps
        VARIABLES       { bt4SwTrapDisplayString,
                          sysName, sysLocation, sysContact }
        DESCRIPTION
                "A bt4SwFwDownloadFailure signifies that firmware 
		 downloaded failed to [image1|image2|boot image]." 
		--#SEVERITY MINOR

        ::= 30 -- 0x1E



bt4SwUfdfoLtMFailure TRAP-TYPE
        ENTERPRISE      bt4Traps
        VARIABLES       { bt4SwTrapDisplayString,
                          sysName, sysLocation, sysContact }
        DESCRIPTION
                "A bt4SwUfdfoLtMFailure trap signifies that a LtM link is down."
                --#SEVERITY MAJOR

        ::= 34 -- 0x22

bt4SwUfdfoLtMUP TRAP-TYPE
        ENTERPRISE      bt4Traps
        VARIABLES       { bt4SwTrapDisplayString,
                          sysName, sysLocation, sysContact }
        DESCRIPTION
                "A bt4SwUfdfoLtMUP trap signifies that a LtM link is up."
                --#SEVERITY INFORMATIONAL

        ::= 35 -- 0x23

bt4SwUfdfoGlobalEna TRAP-TYPE
        ENTERPRISE      bt4Traps
        VARIABLES       { bt4SwTrapDisplayString,
                          sysName, sysLocation, sysContact }
        DESCRIPTION
                "A bt4SwUfdfoGlobalEna trap signifies that Global UFD is enabled."
                --#SEVERITY INFORMATIONAL

        ::= 36 -- 0x24

bt4SwUfdfoGlobalDis TRAP-TYPE
        ENTERPRISE      bt4Traps
        VARIABLES       { bt4SwTrapDisplayString,
                          sysName, sysLocation, sysContact }
        DESCRIPTION
                "A bt4SwUfdfoGlobalDis trap signifies that Global UFD is disabled."
                --#SEVERITY INFORMATIONAL

        ::= 37 -- 0x25


bt4SwUfdfoLtDAutoEna TRAP-TYPE
        ENTERPRISE      bt4Traps
        VARIABLES       { bt4SwTrapDisplayString,
                          sysName, sysLocation, sysContact }
        DESCRIPTION
                "A bt4SwUfdfoLtDAutoEna trap signifies that a LtD link is Auto Enabled."
                --#SEVERITY INFORMATIONAL

        ::= 38 -- 0x26


bt4SwUfdfoLtDAutoDis TRAP-TYPE
        ENTERPRISE      bt4Traps
        VARIABLES       { bt4SwTrapDisplayString,
                          sysName, sysLocation, sysContact }
        DESCRIPTION
                "A bt4SwUfdfoLtDAutoDis trap signifies that a LtD link is Auto Disabled."
                --#SEVERITY INFORMATIONAL

        ::= 39 -- 0x27

bt4SwCubeInserted TRAP-TYPE
        ENTERPRISE      bt4Traps
        VARIABLES       { bt4SwTrapDisplayString,
                          sysName, sysLocation, sysContact }
        DESCRIPTION
                "A Cube was inserted."

                --#SEVERITY INFORMATIONAL

        ::= 40 -- 0x28

bt4SwCubeRemoved TRAP-TYPE
        ENTERPRISE      bt4Traps
        VARIABLES       { bt4SwTrapDisplayString,
                          sysName, sysLocation, sysContact }
        DESCRIPTION
                "A Cube was removed."

                --#SEVERITY INFORMATIONAL

        ::= 41 -- 0x29
END
