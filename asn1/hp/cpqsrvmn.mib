-- ****************************************************************************
-- :CPQ,DEV:
--
-- * COMPAQ SERVER MANAGER/R SNMP MIB DEFINITIONS
--
-- * $Date: 2003/06/10 23:27:40 $
-- * $Revision: 1.1 $
--
-- Compaq Computer Corporation
-- Confidential - Need To Know
-- ****************************************************************************
-- :CPQ,ENDDEV:
--
--                       Compaq Server Manager/R
--         Management Information Base for SNMP Network Management
--
--
--      Copyright 1997, Compaq Computer Corporation.
--      All Rights Reserved.
--
--      The information in this document is subject to change without notice.
--     
--      COMPAQ COMPUTER CORPORATION SHALL NOT BE LIABLE FOR TECHNICAL
--      OR EDITORIAL ERRORS OR OMISSIONS CONATINED HEREIN; NOR FOR INCIDENTAL
--      OR CONSEQUENTIAL DAMAGES RESULTING FROM THE FURNISHING, PERFORMANCE,
--      OR USE OF THIS MATERIAL.
--
-- 	Refer to the READMIB.RDM file for more information about the 
--      organization of the information in the Compaq Enterprise.
--
--      The Compaq Enterprise number is 232.
--      The ASN.1 prefix to, and including the Compaq Enterprise is:
--           1.3.6.1.4.1.232
--
-- ****************************************************************************

CPQSRVMN-MIB DEFINITIONS ::= BEGIN

    IMPORTS
        compaq                  FROM CPQHOST-MIB
        enterprises             FROM RFC1155-SMI
        Counter                 FROM RFC1155-SMI
        DisplayString           FROM RFC1213-MIB
        OBJECT-TYPE             FROM RFC-1212
        TRAP-TYPE               FROM RFC-1215;

--  compaq              OBJECT IDENTIFIER ::= { enterprises 232 }

    cpqServerManager    OBJECT IDENTIFIER ::= { compaq 4 }
    cpqSmMibRev         OBJECT IDENTIFIER ::= { cpqServerManager 1 }
    cpqSmComponent      OBJECT IDENTIFIER ::= { cpqServerManager 2 }
    cpqSmTrap           OBJECT IDENTIFIER ::= { cpqServerManager 3 }

    cpqSmInterface      OBJECT IDENTIFIER ::= { cpqSmComponent 1 }
    cpqSmCntlr          OBJECT IDENTIFIER ::= { cpqSmComponent 2 }
    cpqSmObjData        OBJECT IDENTIFIER ::= { cpqSmComponent 3 }
    cpqSmAsyncComm      OBJECT IDENTIFIER ::= { cpqSmComponent 4 }
    cpqSmAlert          OBJECT IDENTIFIER ::= { cpqSmComponent 5 }

    cpqSmOsNetWare3x    OBJECT IDENTIFIER ::= { cpqSmInterface 1 }

-- :CPQ,DEV:
--   Do not implement MIB Revision table for Insight v2.00.
--
-- ****************************************************************************
--   Server Manager/R MIB Revision
--   =============================
--
-- The compaq enterprise               (232)
--      cpqServerManager Group         (232.4)
--       cpqSmMibRev Group             (232.4.1)
--      
--      Implementation of the cpqSmMibRev group is mandatory for all agents
--      supporting the Compaq Server Manager MIB.
--
--      An SNMP agent conforming to this document will return a
--      cpqSmMibRevMajor of one and a cpqSmMibRevMinor of zero. 
--
-- ****************************************************************************


    cpqSmMibRevMajor OBJECT-TYPE
        SYNTAX  INTEGER (1..65535)
        ACCESS  read-only
        STATUS  mandatory
        DESCRIPTION
            "The Major Revision level.  

             A change in the major revision level represents a major 
             change in the architecture of the MIB.  A change in the 
             major revision level may indicate a significant change in 
             the information supported and/or the meaning of the supported 
             information, correct interpretation of data may require a MIB
             document with the same major revision level."
        ::= { cpqSmMibRev 1 }

    cpqSmMibRevMinor OBJECT-TYPE
        SYNTAX  INTEGER (0..65535)
        ACCESS  read-only
        STATUS  mandatory
        DESCRIPTION
            "The Minor Revision level.  

             A change in the minor revision level may represent some 
             minor additional support, no changes to any pre-existing 
             information has occurred."
        ::= { cpqSmMibRev 2 }


-- :CPQ,ENDDEV:

-- ****************************************************************************
--    Server Manager NetWare Driver Group
--    ===================================
--
-- The compaq enterprise               (232)
--      cpqServerManager Group         (232.4)
--       cpqSmComponent Group          (232.4.2)
--        cpqSmInterface Group         (232.4.2.1)
--         cpqSmOsNetWare3x Group      (232.4.2.1.1)
-- 
--      The cpqSmOsNetWare3x group describes the Server Manager NetWare v3.x
--      OS interface.  This information describes the driver module and its
--      status.
--
--      Implementation of the cpqSmOsNetWare3x group is mandatory for all
--      agents that support the Compaq Server Manager MIB in a NetWare 
--      host operating environment.
--
-- ****************************************************************************

    cpqSmNw3xDriverName OBJECT-TYPE
        SYNTAX  DisplayString (SIZE (0..255))
        ACCESS  read-only
        STATUS  mandatory
        DESCRIPTION
            "Driver Name.

            This value identifies the NetWare loadable module providing the
            operating system access to the Server Manager board."
        ::= { cpqSmOsNetWare3x 1 }

    cpqSmNw3xDriverDate OBJECT-TYPE
        SYNTAX  DisplayString (SIZE (8))
        ACCESS  read-only
        STATUS  mandatory
        DESCRIPTION
            "Driver Date.

            The date of the NetWare loadable module providing the operating
            system access to the Server Manager board.  The date is provided
            in mm/dd/yy format."
        ::= { cpqSmOsNetWare3x 2 }

    cpqSmNw3xDriverVersion OBJECT-TYPE
        SYNTAX  DisplayString (SIZE (0..5))
        ACCESS  read-only
        STATUS  mandatory
        DESCRIPTION
            "Driver Version.

            This is the version of the NetWare Loadable Module (NLM) 
            providing the operating system access to the Server Manager 
            board.  Version 1.20 or greater of the driver is required 
            to use the Server Manager SNMP agent."
        ::= { cpqSmOsNetWare3x 3 }

    cpqSmNw3xDriverIssuedCommands OBJECT-TYPE
        SYNTAX  Counter
        ACCESS  read-only
        STATUS  mandatory
        DESCRIPTION
            "Server Manager Commands Sent.
            
            The number of commands the driver has issued to the Server
            Manager board since it was loaded."
        ::= { cpqSmOsNetWare3x 4 }

    cpqSmNw3xDriverReceivedCommands OBJECT-TYPE
        SYNTAX  Counter
        ACCESS  read-only
        STATUS  mandatory
        DESCRIPTION
            "Server Manager Commands Received.
            
            The number of commands the driver has received from the Server
            Manager board since it was loaded."
        ::= { cpqSmOsNetWare3x 5 }

    cpqSmNw3xDriverWatchdogFrequency OBJECT-TYPE
        SYNTAX  INTEGER (0..255)
        ACCESS  read-only
        STATUS  mandatory
        DESCRIPTION
            "Server Manager Watchdog Frequency.
            
            The number of minutes between watchdog commands.  The watchdog
            command is the way the Server Manager board determines that the
            driver and NetWare are still running.  A value of zero (0) 
            means no watchdog is being performed."
        ::= { cpqSmOsNetWare3x 6 }

    cpqSmNw3xDriverClockSyncFrequency OBJECT-TYPE
        SYNTAX  INTEGER (0..65535)
        ACCESS  read-only
        STATUS  mandatory
        DESCRIPTION
            "Server Manager Clock Sync Frequency.
            
            The number of minutes between clock synchronization commands.
            The clock synchronization command sets the Server Manager board's
            clock to the same value as the NetWare OS clock.  A value of 
            zero (0) means no clock synchronization is being performed."
        ::= { cpqSmOsNetWare3x 7 }

    cpqSmNw3xDriverIssuedWatchdogs OBJECT-TYPE
        SYNTAX  Counter
        ACCESS  read-only
        STATUS  mandatory
        DESCRIPTION
            "Server Manager Watchdog Commands Issues.
            
            The number of watch dog commands issued since the driver was 
            loaded."
        ::= { cpqSmOsNetWare3x 8 }

    cpqSmNw3xDriverIssuedClockSyncs OBJECT-TYPE
        SYNTAX  Counter
        ACCESS  read-only
        STATUS  mandatory
        DESCRIPTION
            "Server Manager Clock Sync Commands Issues.
            
            The number of clock synchronization commands performed since the
            driver was loaded."
        ::= { cpqSmOsNetWare3x 9 }

    cpqSmNw3xDriverMemoryAllocationFailedErrs OBJECT-TYPE
        SYNTAX  Counter
        ACCESS  read-only
        STATUS  mandatory
        DESCRIPTION
            "Server Manager Memory Allocation Errors.
            
            The number of times that a memory allocation failed when a 
            command received by the driver required a buffer to be
            allocated."
        ::= { cpqSmOsNetWare3x 10 }

    cpqSmNw3xDriverBoardResets OBJECT-TYPE
        SYNTAX  Counter
        ACCESS  read-only
        STATUS  mandatory
        DESCRIPTION
            "Server Manager Board Resets.
            
            The number of times the driver detected the Server Manager board
            resetting itself."
        ::= { cpqSmOsNetWare3x 11 }

    cpqSmNw3xBoardState OBJECT-TYPE
        SYNTAX  INTEGER {
                other(1),
                ok(2),
                failed(3)
                }
        ACCESS  read-only
        STATUS  mandatory
        DESCRIPTION
            "Server Manager Board State.
            
            The driver's perception of the Server Manager board's state."
        ::= { cpqSmOsNetWare3x 12 }



-- ****************************************************************************
--     Server Manager Controller Information Group
--     ===========================================
--
-- The compaq enterprise               (232)
--      cpqServerManager Group         (232.4)
--       cpqSmComponent Group          (232.4.2)
--        cpqSmCntrl Group             (232.4.2.2)
--
--      The cpqSmCntlr group contains the configuration and statistical
--      information of the Server Manager controller.
--
--      Implementation of the cpqSmCntlr group is mandatory for all agents
--      that support the Compaq Server Manager MIB.
--
-- ****************************************************************************

    cpqSmCntlrBoardName OBJECT-TYPE
        SYNTAX  DisplayString (SIZE (0..15))
        ACCESS  read-only
        STATUS  mandatory
        DESCRIPTION
            "Server Manager Board Name.
            
            The name of the Server Manager board supplied by the user
            during configuration of the Server Manager board using the EISA
            Configuration Utility."
        ::= { cpqSmCntlr 1 }

    cpqSmCntlrBoardId OBJECT-TYPE
        SYNTAX  DisplayString (SIZE (0..5))
        ACCESS  read-only
        STATUS  mandatory
        DESCRIPTION
            "Server Manager Board ID.
            
            The ID of the Server Manager board supplied by the user
            during configuration of the Server Manager board using the EISA
            Configuration Utility."
        ::= { cpqSmCntlr 2 }

    cpqSmCntlrRomDate OBJECT-TYPE
        SYNTAX  DisplayString (SIZE (8))
        ACCESS  read-only
        STATUS  mandatory
        DESCRIPTION
            "Server Manager ROM Date.
            
            The date of the firmware on the board in mm/dd/yy format."
        ::= { cpqSmCntlr 3 }

    cpqSmCntlrCountryCode OBJECT-TYPE
        SYNTAX  DisplayString (SIZE (2))
        ACCESS  read-only
        STATUS  mandatory
        DESCRIPTION
            "Server Manager Country Code.
            
            An abbreviation for the country (language) for which the Server
            Manager board is configured.  The possible values are:

                AE      Arabic - English
                AF      Arabic - French
                AU      Australia
                BE      Belgium
                BF      Belgium - Flemish
                CE      Canadian - English
                CF      Canadian - French
                CH      China
                DN      Denmark
                DU      Dutch
                EE      European - English
                FN      Finland
                FR      France
                GR      Germany
                HA      Hungary
                IT      Italy
                IS      Israel
                KA      Kangi
                LA      Latin America
                ME      Middle East
                NE      Netherlands
                NO      Norway
                PO      Portugal
                SP      Spain
                SW      Sweden
                ST      Switzerland
                SF      Swiss - French
                SG      Swiss - German
                TA      Taiwan
                UK      United Kingdom
                US      United States"
        ::= { cpqSmCntlr 4 }

    cpqSmCntlrVoiceRomStatus OBJECT-TYPE
        SYNTAX  INTEGER {
                other(1),
                notInstalled(2),
                installed(3)
                }
        ACCESS  read-only
        STATUS  mandatory
        DESCRIPTION
            "Server Manager Voice ROM Status.
            
            The value specifies if the Server Manager board has a voice ROM
            installed."
        ::= { cpqSmCntlr 5 }

    cpqSmCntlrBatteryStatus OBJECT-TYPE
        SYNTAX  INTEGER {
                other(1),
                connected(2),
                disconnected(3)
                }
        ACCESS  read-only
        STATUS  mandatory
        DESCRIPTION
            "Server Manager Battery Connection Status."
        ::= { cpqSmCntlr 6 }

    cpqSmCntlrDormantModeStatus OBJECT-TYPE
        SYNTAX  INTEGER {
                other(1),
                normal(2),
                dormantOnPowerDown(3)
                }
        ACCESS  read-only
        STATUS  mandatory
        DESCRIPTION
            "Server Manager Dormant Mode Status.
            
            The status of the power management system."
        ::= { cpqSmCntlr 7 }

    cpqSmCntlrSelfTestErrorCode OBJECT-TYPE
        SYNTAX  INTEGER (0..65535)
        ACCESS  read-only
        STATUS  mandatory
        DESCRIPTION
            "Server Manager Self Test Error Code.
            
            The result of the self test run by the Server Manager board
            firmware.  This value is a set of bit flags defined as follows
            (bit 0 is the least significant bit):
                Bit 0 set  - ROM Checksum failed
                Bit 1 set  - RAM test failed
                Bit 2 set  - 80186 timer failed
                Bit 3 set  - Built in modem failed
                Bit 4 set  - Direct connect interface failed
                Bit 5 set  - Real time clock failed
                Bit 6 set  - Temperature and/or voltage sensor failed
                Bit 7 set  - DTMF (tone detection circuitry) failed
                Bit 8 set  - VSL (voice synthesis logic circuitry) failed
                Bit 9 set  - Host bus monitor failed
                Bit 10 set - Bus master interface failed
                Bit 11 set - Battery is broken

            Bits 12 - 15 are currently reserved.

            A value of zero (no bits are set) indicates no self test error 
            has occured."
        ::= { cpqSmCntlr 8 }

    cpqSmCntlrOsId OBJECT-TYPE
        SYNTAX  INTEGER {
                other(1),
                netware286(177),
                netware386(178),
                os2LanManager(179),
                unix(180),
                banyan(181),
                dos(182)
                }
        ACCESS  read-only
        STATUS  mandatory
        DESCRIPTION
            "Server Manager Operating System ID.
            
            The host operating system registered by the driver with the
            Server Manager board."
        ::= { cpqSmCntlr 9 }

    cpqSmCntlrOsMajorRev OBJECT-TYPE
        SYNTAX  INTEGER (0..255)
        ACCESS  read-only
        STATUS  mandatory
        DESCRIPTION
            "Server Manager Operating System Major Revision.
            
            The major revision of the host operating system registered by
            the driver with the Server Manager board."
        ::= { cpqSmCntlr 10 }

    cpqSmCntlrOsMinorRev OBJECT-TYPE
        SYNTAX  INTEGER (0..255)
        ACCESS  read-only
        STATUS  mandatory
        DESCRIPTION
            "Server Manager Operating System Minor Revision.
            
            The minor revision of the host operating system registered by
            the driver with the Server Manager board."
        ::= { cpqSmCntlr 11 }

    cpqSmCntlrPostTimeout OBJECT-TYPE
        SYNTAX  INTEGER (0..60)
        ACCESS  read-only
        STATUS  mandatory
        DESCRIPTION
            "Server Manager Power On Self Test Timeout.
            
            The number of minutes the board should wait for POST to
            complete.  A value of 0 indicates that the version of firmware
            on the Server Manager board does not make this information
            available."
        ::= { cpqSmCntlr 12 }

    cpqSmCntlrCondition OBJECT-TYPE
        SYNTAX  INTEGER {
            other(1),
            ok(2),
            degraded(3),
            failed(4)
        }
    ACCESS  read-only
    STATUS  mandatory
    DESCRIPTION
        "Server Manager Condition.
            
         This represents the overall condition of the Server Manager board."
-- :CPQ,DEV:
--	ok(2): Everything on the board is working (to best of our knowledge).
-- 
-- 	degraded(3): The board is running and the OS is capable of 
--               communicating with it.  However, the on-board diagnostic 
--               has reported a failure in one or more subsystems.
-- 	    
-- 	failed(4): The board is not accepting commands from the OS.
-- 
-- Here is the proposed algorithm.
-- 
-- OK:		Board accecpts and processes commands.	AND
-- 		No Self Test Error Code Exists.		AND
-- 		No Board Reset has occured since the driver was loaded.  AND
-- 		The Board is NOT returning 0x1A (Board Failed).
-- 
-- Degraded:	Board accepts and processes commands.  AND
-- 		The Board is NOT returning a 0x1A (Board Failed)    AND
-- 
-- 		A non-zero Self Test Error Code exists.   OR
-- 		A board reset has occured since the driver was loaded.
-- 		
-- Failed:		The board is NOT accepting Commands.      OR
-- 		The driver has timed out the board.		OR
-- 		The board is returning 0x1A (Board Failed)	OR
-- 		The board has reset, and the recovery is pending.
-- :CPQ,ENDDEV:
    ::= { cpqSmCntlr 13 }

-- ****************************************************************************
--   Server Manager Object Data Group
--   ================================
--
-- The compaq enterprise               (232)
--      cpqServerManager Group         (232.4)
--       cpqSmComponent Group          (232.4.2)
--        cpqSmObjData Group           (232.4.2.3)
--
--      The cpqSmObjData group contains lists and describes the objects and
--      monitored items on the Server Manager board.  The cpqSmObjData group
--      also provides some information about the Server Manager board's
--      object management resource utilization.
--
--      Implementation of the cpqSmObjData group is mandatory for all agents
--      that support the Compaq Server Manager MIB.
--
-- ****************************************************************************

    cpqSmObjDataTotalObjects OBJECT-TYPE
        SYNTAX  INTEGER (0..65535)
        ACCESS  read-only
        STATUS  mandatory
        DESCRIPTION
            "Server Manager Total Objects.
            
            The total number of objects currently defined on the Server
            Manager Board."
        ::= { cpqSmObjData 1 }

    cpqSmObjDataObjectTotalSpace OBJECT-TYPE
        SYNTAX  INTEGER (0..65535)
        ACCESS  read-only
        STATUS  mandatory
        DESCRIPTION
            "Server Manager Total Object Space.
            
            The total amount of memory on the Server Manager board for
            storing object and monitored item information.  This number is
            given in Server Manager board specific unit type and is best used
            in comparison with the objDataObjectSpaceAvailable."
        ::= { cpqSmObjData 2 }

    cpqSmObjDataObjectSpaceAvailable OBJECT-TYPE
        SYNTAX  INTEGER (0..65535)
        ACCESS  read-only
        STATUS  mandatory
        DESCRIPTION
            "Server Manager Available Object Space.
            
            The amount of memory currently available on the Server Manager
            board for storing object and monitored item information.  This
            number is given in a Server Manager board specific unit type and
            is best used in comparison with the objDataObjectTotalSpace."
        ::= { cpqSmObjData 3 }

    cpqSmObjDataInnateMonitoringStatus OBJECT-TYPE
        SYNTAX  INTEGER {
                other(1),
                disabled(2),
                enabled(3)
                }
        ACCESS  read-only
        STATUS  mandatory
        DESCRIPTION
            "Server Manager Innate Monitoring Status.

            The following values are valid:

                Enabled (3)     Innate Monitoring is active.

                Disabled (2)    Innate Monitoring is not active.

                Other (1)       Innate Monitoring status is unobtainable

            Innate Monitoring is performed by the Server Manager board
            without input from the operating system.  It includes monitoring
            of information such as Temperature, Input/Output Check, and
            Power.  

            Compaq DIAGNOSTICS disables Innate Monitoring before executing
            any tests so that alerts are not caused inadvertently.  After
            completion, Diagnostics re-enables alerting."
        ::= { cpqSmObjData 4 }


-- ****************************************************************************
--     Server Manager Object Data Table
--     ================================
--
-- The compaq enterprise               (232)
--      cpqServerManager Group         (232.4)
--       cpqSmComponent Group          (232.4.2)
--        cpqSmObjData Group           (232.4.2.3)
--         cpqSmObjectTable            (232.4.2.3.1)
--
-- ****************************************************************************

    cpqSmObjectTable OBJECT-TYPE
        SYNTAX  SEQUENCE OF CpqSmObjectEntry
        ACCESS  not-accessible
        STATUS  mandatory
        DESCRIPTION
            "A list of the objects currently defined on the Server Manager
            board."
        ::= { cpqSmObjData 5 }

    cpqSmObjectEntry OBJECT-TYPE
        SYNTAX  CpqSmObjectEntry
        ACCESS  not-accessible
        STATUS  mandatory
        DESCRIPTION
            "A description of an object currently defined on the Server
            Manager board."
        INDEX   { cpqSmObjectIndex, cpqSmObjectInstIndex }
        ::= { cpqSmObjectTable 1 }

    CpqSmObjectEntry ::= SEQUENCE {
        cpqSmObjectIndex         INTEGER,
        cpqSmObjectInstIndex     INTEGER,
        cpqSmObjectClass         INTEGER,
        cpqSmObjectLabel         DisplayString
    }

    cpqSmObjectIndex OBJECT-TYPE
        SYNTAX  INTEGER (1..4294967295)
        ACCESS  read-only
        STATUS  mandatory
        DESCRIPTION
            "This is a number that uniquely specifies a type of object on
            the Server Manager board."
        ::= { cpqSmObjectEntry 1 }

    cpqSmObjectInstIndex OBJECT-TYPE
        SYNTAX  INTEGER (0..255)
        ACCESS  read-only
        STATUS  mandatory
        DESCRIPTION
            "This number uniquely specifies a particular instance of an
            object on the Server Manager board."
        ::= { cpqSmObjectEntry 2 }

    cpqSmObjectClass OBJECT-TYPE
        SYNTAX  INTEGER
        ACCESS  read-only
        STATUS  mandatory
        DESCRIPTION
            "A number used to group associated objects together by the type
            of function they perform.  The currently defined classes are:
            
                4096    (1000 hex)  System Board
                8192    (2000 hex)  Disk Storage
                16384   (4000 hex)  Tape Storage
                20480   (5000 hex)  Network
                24576   (6000 hex)  NetWare
                28672   (7000 hex)  SCO UNIX
                32768   (8000 hex)  OS/2 LAN Manager
                36864   (9000 hex)  Banyan VINES"
        ::= { cpqSmObjectEntry 3 }

    cpqSmObjectLabel OBJECT-TYPE
        SYNTAX  DisplayString (SIZE (0..15))
        ACCESS  read-only
        STATUS  mandatory
        DESCRIPTION
            "A short text description of the object."
        ::= { cpqSmObjectEntry 4 }


-- ****************************************************************************
--   Server Manager Monitored Item Table
--   ===================================
--
-- The compaq enterprise               (232)
--      cpqServerManager Group         (232.4)
--       cpqSmComponent Group          (232.4.2)
--        cpqSmObjData Group           (232.4.2.3)
--         cpqSmMonItemTable           (232.4.2.3.6)
--
-- ****************************************************************************

    cpqSmMonItemTable OBJECT-TYPE
        SYNTAX  SEQUENCE OF CpqSmMonItemEntry
        ACCESS  not-accessible
        STATUS  mandatory
        DESCRIPTION
            "A list of the monitored items currently defined on the Server
            Manager board."
        ::= { cpqSmObjData 6 }

    cpqSmMonItemEntry OBJECT-TYPE
        SYNTAX  CpqSmMonItemEntry
        ACCESS  not-accessible
        STATUS  mandatory
        DESCRIPTION
            "A description of a monitored item currently defined on the
            Server Manager board."
        INDEX   { cpqSmMonItemObjIndex, cpqSmMonItemInstIndex, 
                cpqSmMonItemIndex }
        ::= { cpqSmMonItemTable 1 }

    CpqSmMonItemEntry ::= SEQUENCE {
        cpqSmMonItemObjIndex             INTEGER,
        cpqSmMonItemInstIndex            INTEGER,
        cpqSmMonItemIndex                INTEGER,
        cpqSmMonItemOnNetAlertStatus     INTEGER,
        cpqSmMonItemRemoteAlertStatus    INTEGER,
        cpqSmMonItemInnateStatus         INTEGER,
        cpqSmMonItemHostNotify           INTEGER,
        cpqSmMonItemLogicalOperator      INTEGER,
        cpqSmMonItemSeverity             INTEGER,
        cpqSmMonItemDataType             INTEGER,
        cpqSmMonItemVoiceMsgNum          INTEGER,
        cpqSmMonItemLabel                DisplayString,
        cpqSmMonItemLimit                INTEGER,
        cpqSmMonItemOptional             INTEGER,
        cpqSmMonItemDefVal               INTEGER,
        cpqSmMonItemCurVal               INTEGER,
        cpqSmMonItemCurString            DisplayString,
        cpqSmMonItemCurContents          OCTET STRING,
        cpqSmMonItemTimeStamp            OCTET STRING
    }

    cpqSmMonItemObjIndex OBJECT-TYPE
        SYNTAX  INTEGER (0..4294967295)
        ACCESS  read-only
        STATUS  mandatory
        DESCRIPTION
            "This number uniquely specifies a type of object on
            the Server Manager board with which this monitored item is
            associated."
        ::= { cpqSmMonItemEntry 1 }

    cpqSmMonItemInstIndex OBJECT-TYPE
        SYNTAX  INTEGER (0..255)
        ACCESS  read-only
        STATUS  mandatory
        DESCRIPTION
            "This number uniquely specifies a particular instance
            of an object on the Server Manager board that with which this
            monitored item is associated."
        ::= { cpqSmMonItemEntry 2 }

    cpqSmMonItemIndex OBJECT-TYPE
        SYNTAX  INTEGER (0..255)
        ACCESS  read-only
        STATUS  mandatory
        DESCRIPTION
            "This number specifies the monitored item of the object
            and instance given in the first two fields that this entry
            describes."
        ::= { cpqSmMonItemEntry 3 }

    cpqSmMonItemOnNetAlertStatus OBJECT-TYPE
        SYNTAX  INTEGER {
                other(1),
                disabled(2),
                enabled(3)
                }
        ACCESS  read-only
        STATUS  mandatory
        DESCRIPTION
            "This field indicates if the driver will be notified when
            this monitored item crosses a defined threshold.  The driver may
            provide some mechanism for logging the event or notifying
            specified users.
            
            This field is undefined if the monItemDataType is string, data,
            or queue."
        ::= { cpqSmMonItemEntry 4 }

    cpqSmMonItemRemoteAlertStatus OBJECT-TYPE
        SYNTAX  INTEGER {
                other(1),
                disabled(2),
                enabled(3)
                }
        ACCESS  read-only
        STATUS  mandatory
        DESCRIPTION
            "This field indicates if the Server Manager board will
            notify pagers, telephones, or Server Manager Facilities when
            this monitored item crosses a defined threshold.
            
            This field is undefined if the monItemDataType is string, data,
            or queue."
        ::= { cpqSmMonItemEntry 5 }

    cpqSmMonItemInnateStatus OBJECT-TYPE
        SYNTAX  INTEGER {
                other(1),
                externallyManaged(2),
                innate(3)
                }
        ACCESS  read-only
        STATUS  mandatory
        DESCRIPTION
            "This field indicates if the Server Manager board is responsible
            for monitoring the value of this monitored item or if an external
            operating system agent is acquiring the value and placing the
            data on the Server Manager board."
        ::= { cpqSmMonItemEntry 6 }

    cpqSmMonItemHostNotify OBJECT-TYPE
        SYNTAX  INTEGER {
                other(1),
                disabled(2),
                enabled(3)
                }
        ACCESS  read-only
        STATUS  mandatory
        DESCRIPTION
            "This field indicate if the operating system driver is to be
            notified of modifications to this monitored item's thresholds."
        ::= { cpqSmMonItemEntry 7 }

    cpqSmMonItemLogicalOperator OBJECT-TYPE
        SYNTAX  INTEGER {
                other(1),
                equal(2),
                notEqual(3),
                lessThan(4),
                greaterThan(5),
                lessThanOrEqual(6),
                greaterThanOrEqual(7),
                inside(8),
                outside(9)
                }
        ACCESS  read-only
        STATUS  mandatory
        DESCRIPTION
            "This shows the logical operation that is done with the limit
            (and optional) to determine if an alerting event has occured.
            
            This field is undefined if the monItemDataType is string, data,
            or queue."
        ::= { cpqSmMonItemEntry 8 }

    cpqSmMonItemSeverity OBJECT-TYPE
        SYNTAX  INTEGER {
                other(1),
                status(2),
                warning(3),
                critical(4),
                catastrophic(5)
                }
        ACCESS  read-only
        STATUS  mandatory
        DESCRIPTION
            "The severity of a problem with this monitored item.
            
            This field is undefined if the monItemDataType is string, data,
            or queue."
        ::= { cpqSmMonItemEntry 9 }

    cpqSmMonItemDataType OBJECT-TYPE
        SYNTAX  INTEGER {
                other(1),
                counter(2),
                state(3),
                range(4),
                string(5),
                data(6),
                queue(7)
                }
        ACCESS  read-only
        STATUS  mandatory
        DESCRIPTION
            "The conceptual type of data of this monitored item."
        ::= { cpqSmMonItemEntry 10 }

    cpqSmMonItemVoiceMsgNum OBJECT-TYPE
        SYNTAX  INTEGER  (0..511)
        ACCESS  read-only
        STATUS  mandatory
        DESCRIPTION
            "The voice message number that would be delivered as part of a
            voice alert when this monitored item exceeds its threshold.
            
            This field is undefined if the monItemDataType is string, data,
            or queue."
        ::= { cpqSmMonItemEntry 11 }

    cpqSmMonItemLabel OBJECT-TYPE
        SYNTAX  DisplayString (SIZE (0..15))
        ACCESS  read-only
        STATUS  mandatory
        DESCRIPTION
            "A short text description of the monitored item."
        ::= { cpqSmMonItemEntry 12 }

    cpqSmMonItemLimit OBJECT-TYPE
        SYNTAX  INTEGER
        ACCESS  read-only
        STATUS  mandatory
        DESCRIPTION
            "Threshold information for this monitored item.
            
            The interpretation of this field depends on the monItemDataType
            field.
            
            For counters this is the value that when passed, as specified by
            the comparator, an alert will occur.  The optional can be used to 
            specify a step.  Whenever the value of the monitored item passes
            the value of the limit plus an integer multiple of the step a 
            new alert will occur.

            For states this is the value that when passed, as specified by
            the comparator, an alert will occur.

            For ranges this value (the low threshold) and the value of the
            optional (the high threshold) define a range.  When the range
            boundaries are crossed, as specified by the comparator, an alert
            will occur.

            This field is undefined if the monItemDataType is string, data,
            or queue."
        ::= { cpqSmMonItemEntry 13 }

    cpqSmMonItemOptional OBJECT-TYPE
        SYNTAX  INTEGER 
        ACCESS  read-only
        STATUS  mandatory
        DESCRIPTION
            "Threshold information for this monitored item.   
             The interpretation of this field depends on the 
             monItemDataType field.
            
             For counters this is the step.  Whenever the value of the
             monitored item passes the value of the limit plus an integer
             multiple of the step a new alert will occur.

             For ranges this value (the high threshold) and the value of the
             limit (the low threshold) define a range.  When the range
             boundaries are crossed, as specified by the comparator, an alert
             will occur.

             This field is undefined if the monItemDataType is state, string,
             data, or queue."
        ::= { cpqSmMonItemEntry 14 }

    cpqSmMonItemDefVal OBJECT-TYPE
        SYNTAX  INTEGER
        ACCESS  read-only
        STATUS  mandatory
        DESCRIPTION
            "Default value information for this monitored item.  Certain
            Server Manager data types support a reset function.  This 
            field specifies the value that the monitored item will change
            to when a reset command is received.  This field is only valid if
            the monItemDataType value is counter, state, or range.  This
            field is undefined if the monItemDataType is string, data, or
            queue."
        ::= { cpqSmMonItemEntry 15 }

    cpqSmMonItemCurVal OBJECT-TYPE
        SYNTAX  INTEGER
        ACCESS  read-only
        STATUS  mandatory
        DESCRIPTION
            "The value of the monitored item if the monitored item's data
            type is counter, state, or range.  If the monitored item's data
            type is string, data, or queue this value is undefined."
        ::= { cpqSmMonItemEntry 16 }

    cpqSmMonItemCurString OBJECT-TYPE
        SYNTAX  DisplayString (SIZE (0..255))
        ACCESS  read-only
        STATUS  mandatory
        DESCRIPTION
            "The value of the monitored item if the monItemDataType is
            string.  If the monItemDataType is counter, state, range, data,
            or queue this value is undefined."
        ::= { cpqSmMonItemEntry 17 }

    cpqSmMonItemCurContents OBJECT-TYPE
        SYNTAX  OCTET STRING (SIZE (0..256))
        ACCESS  read-only
        STATUS  mandatory
        DESCRIPTION
            "The value of the monitored item if the monItemDataType is data
            or queue.  If the monItemDataType is counter, state, range, or
            string this value is undefined.
            
            If the monItemDataType is data this field will contain a length
            octet (byte) followed by a number of octets of data equal to the
            value of the length octet.
            
            If the monItemDataType is queue this field will contain a head of
            queue octet followed by 255 octets of data.  The value of the
            head of queue octet indicates the data octet that is the logical
            head of the circular queue of data."
        ::= { cpqSmMonItemEntry 18 }

    cpqSmMonItemTimeStamp OBJECT-TYPE
        SYNTAX  OCTET STRING (SIZE (6))
        ACCESS  read-only
        STATUS  mandatory
        DESCRIPTION
            "An octet string specifying the time of the last change of this
            monitored item.  This octet string contains in the following
            order: year, month, day of month, hour, minute, second.  Each of
            the octets is a Binary Coded Decimal (BCD) number."
        ::= { cpqSmMonItemEntry 19 }

-- ****************************************************************************
--   Server Manager Asynchronous Communications Group
--   ================================================
--
-- The compaq enterprise               (232)
--      cpqServerManager Group         (232.4)
--       cpqSmComponent Group          (232.4.2)
--        cpqSmAsyncComm Group         (232.4.2.4)
--
--      The cpqSmAsyncComm group describes the configuration and status of
--      the Server Manager board's asynchronous communication ports.
--
--      Implementation of the cpqSmAsyncComm group is mandatory for all
--      agents that support the Compaq Server Manager MIB.
--
-- ****************************************************************************


    cpqSmCommAsyncCommunicationStatus OBJECT-TYPE
        SYNTAX  INTEGER {
                other(1),
                disabled(2),
                enabled(3)
                }
        ACCESS  read-only
        STATUS  mandatory
        DESCRIPTION
            "Async Status.

            This shows if asynchronous communication with the Server
            Manager's serial interface and modem is enabled (3) or 
            disabled (2).

            This feature can be enabled or disabled through the Collection
            Agent User Interface (CPQCAUI.NLM).

            You may want to disable the Async Communication with the Server
            Manager to prevent a Server Manager Facility (SMF) user from
            assuming control of the system console.  Disabling the Async
            Communication disconnects any active SMF session.   Disabling the
            Async Communications also disables all remote alerts.  Server
            Manager On-the-Network alerts will remain enabled. On-the-Network
            alerts are those sent over the network."
        ::= { cpqSmAsyncComm 1 }

    cpqSmCommInternalModemMaxBaudRate OBJECT-TYPE
        SYNTAX  INTEGER (0..2147483647)
        ACCESS  read-only
        STATUS  mandatory
        DESCRIPTION
            "The value specifies the maximum baud rate supported by the modem
            installed on the Server Manager board.  A value of 0 indicates
            that the version of firmware on the Server Manager board does not
            make this information available."
        ::= { cpqSmAsyncComm 2 }

    cpqSmCommAudibleIndicatorStatus OBJECT-TYPE
        SYNTAX  INTEGER {
                other(1),
                disabled(2),
                enabled(3)
                }
        ACCESS  read-only
        STATUS  mandatory
        DESCRIPTION
            "The current status of the remote console audible indicator.
            
            When enabled, the server will beep when the Server Manager is
            being used by a Server Manager Facility for remote session
            emulation."
        ::= { cpqSmAsyncComm 3 }

    cpqSmCommRemoteSessionStatus OBJECT-TYPE
        SYNTAX  INTEGER {
                other(1),
                notSupported(2),
                noSessionActive(3),
                remoteSessionActive(4),
                pgrVoiceSessionActive(5),
                remoteConsoleActive(6)
                }
        ACCESS  read-only
        STATUS  mandatory
        DESCRIPTION
            "The current value of the remote session activity.  A value of
            notSupported indicates that the version of firmware on the Server
            Manager board does not make this information available."
        ::= { cpqSmAsyncComm 4 }

    cpqSmCommCallbackStatus OBJECT-TYPE
        SYNTAX  INTEGER {
                other(1),
                disabled(2),
                enabled(3)
                }
        ACCESS  read-only
        STATUS  mandatory
        DESCRIPTION
            "The status of the call back feature of the Server Manager board."
        ::= { cpqSmAsyncComm 5 }

-- ****************************************************************************
--   Server Manager Modem Setting Table
--   ==================================
--
-- The compaq enterprise               (232)
--      cpqServerManager Group         (232.4)
--       cpqSmComponent Group          (232.4.2)
--        cpqSmAsyncComm Group         (232.4.2.4)
--         cpqSmModemSettingsTable     (232.4.2.4.6)
--
-- ****************************************************************************

    cpqSmModemSettingsTable OBJECT-TYPE
        SYNTAX  SEQUENCE OF CpqSmModemSettingsEntry
        ACCESS  not-accessible
        STATUS  mandatory
        DESCRIPTION
            "The list of defined modem settings for the Server Manager board."
        ::= { cpqSmAsyncComm 6 }

    cpqSmModemSettingsEntry OBJECT-TYPE
        SYNTAX  CpqSmModemSettingsEntry
        ACCESS  not-accessible
        STATUS  mandatory
        DESCRIPTION
            "A defined modem's settings for the Server Manager board."
        INDEX   { cpqSmModemSettingsIndex }
        ::= { cpqSmModemSettingsTable 1 }

    CpqSmModemSettingsEntry ::= SEQUENCE {
        cpqSmModemSettingsIndex              INTEGER,
        cpqSmModemSettingsStatus             INTEGER,
        cpqSmModemSettingsBaudRate           INTEGER,
        cpqSmModemSettingsParity             INTEGER,
        cpqSmModemSettingsDataLength         INTEGER,
        cpqSmModemSettingsStopBits           INTEGER,
        cpqSmModemSettingsDialString         DisplayString,
        cpqSmModemSettingsHangUpString       DisplayString,
        cpqSmModemSettingsAnswerString       DisplayString,
        cpqSmModemSettingsOriginateString    DisplayString
        }

    cpqSmModemSettingsIndex OBJECT-TYPE
        SYNTAX  INTEGER {
                internalModem(48),
                externalModem(49),
                pager(50)
                }
        ACCESS  read-only
        STATUS  mandatory
        DESCRIPTION
            "The type of modem settings this entry describes."
        ::= { cpqSmModemSettingsEntry 1 }

    cpqSmModemSettingsStatus OBJECT-TYPE
        SYNTAX  INTEGER {
            other(1),
            noInternalModem(2),
            internalUSModem(3),
            internalIntnlModem(4),
            serialPortNotSetup(5),
            serialDirectConnect(6),
            serialExternalModem(7),
            pagerInformationData(8)
            }
        ACCESS  read-only
        STATUS  mandatory
        DESCRIPTION
            "Status information about the modem described by this table
            entry.  Only some of these values are appropriate for some types
            of entries."
        ::= { cpqSmModemSettingsEntry 2 }

    cpqSmModemSettingsBaudRate OBJECT-TYPE
        SYNTAX  INTEGER (0..2147483647)
        ACCESS  read-only
        STATUS  mandatory
        DESCRIPTION
            "The baud rate to be used over this communcation medium by the 
            Server Manager board."
        ::= { cpqSmModemSettingsEntry 3 }

    cpqSmModemSettingsParity OBJECT-TYPE
        SYNTAX  INTEGER {
                other(1),
                none(2),
                odd(3),
                even(4)
                }
        ACCESS  read-only
        STATUS  mandatory
        DESCRIPTION
            "The parity used for this communication medium by the Server
            Manager board."
        ::= { cpqSmModemSettingsEntry 4 }

    cpqSmModemSettingsDataLength OBJECT-TYPE
        SYNTAX  INTEGER (0..255)
        ACCESS  read-only
        STATUS  mandatory
        DESCRIPTION
            "The data length used for this communication medium by the 
            Server Manager board."
        ::= { cpqSmModemSettingsEntry 5 }

    cpqSmModemSettingsStopBits OBJECT-TYPE
        SYNTAX  INTEGER (1..2)
        ACCESS  read-only
        STATUS  mandatory
        DESCRIPTION
            "The number of stop bits used for this communication medium by
            the Server Manager board."
        ::= { cpqSmModemSettingsEntry 6 }

    cpqSmModemSettingsDialString OBJECT-TYPE
        SYNTAX  DisplayString (SIZE (0..24))
        ACCESS  read-only
        STATUS  mandatory
        DESCRIPTION
            "The string that is entered before any dial operation by the 
            Server Manager board."
        ::= { cpqSmModemSettingsEntry 7 }

    cpqSmModemSettingsHangUpString OBJECT-TYPE
        SYNTAX  DisplayString (SIZE (0..24))
        ACCESS  read-only
        STATUS  mandatory
        DESCRIPTION
            "The string used to hang up the phone by the Server Manager
            board."
        ::= { cpqSmModemSettingsEntry 8 }

    cpqSmModemSettingsAnswerString OBJECT-TYPE
        SYNTAX  DisplayString (SIZE (0..24))
        ACCESS  read-only
        STATUS  mandatory
        DESCRIPTION
            "The string used to put the modem into auto-answer mode by the 
            Server Manager board."
        ::= { cpqSmModemSettingsEntry 9 }

    cpqSmModemSettingsOriginateString OBJECT-TYPE
        SYNTAX  DisplayString (SIZE (0..24))
        ACCESS  read-only
        STATUS  mandatory
        DESCRIPTION
            "The string used to put the modem into originate mode by the 
            Server Manager board."
        ::= { cpqSmModemSettingsEntry 10 }

-- ****************************************************************************
--   Server Manager Alert Group
--   ==========================
--
-- The compaq enterprise               (232)
--      cpqServerManager Group         (232.4)
--       cpqSmComponent Group          (232.4.2)
--        cpqSmAlert Group             (232.4.2.5)
--
--      The cpqSmAlert group describes the configuration and status and the
--      Server Manager board's alerting system.
--
--      Implementation of the cpqSmAlert group is mandatory for all agents
--      that support the Compaq Server Manager MIB.
--
-- ****************************************************************************


    cpqSmAlertStatus OBJECT-TYPE
        SYNTAX  INTEGER {
                other(1),
                disabled(2),
                enabled(3)
                }
        ACCESS  read-only
        STATUS  mandatory
        DESCRIPTION
            "The current alerting status."
        ::= { cpqSmAlert 1 }

-- ****************************************************************************
--   Server Manager Alert Destination Table
--   ======================================
--
-- The compaq enterprise               (232)
--      cpqServerManager Group         (232.4)
--       cpqSmComponent Group          (232.4.2)
--        cpqSmAlert Group             (232.4.2.5)
--         cpqSmAlertDestTable         (232.4.2.5.2)
--
-- ****************************************************************************

    cpqSmAlertDestTable OBJECT-TYPE
        SYNTAX  SEQUENCE OF CpqSmAlertDestEntry
        ACCESS  not-accessible
        STATUS  mandatory
        DESCRIPTION
            "The list of currently defined alert destinations on the Server
            Manager board."
        ::= { cpqSmAlert 2 }

    cpqSmAlertDestEntry OBJECT-TYPE
        SYNTAX  CpqSmAlertDestEntry
        ACCESS  not-accessible
        STATUS  mandatory
        DESCRIPTION
            "A currently defined alert destination on the Server Manager
            board."
        INDEX   { cpqSmAlertDestPriorityIndex }
        ::= { cpqSmAlertDestTable 1 }

    CpqSmAlertDestEntry ::= SEQUENCE {
        cpqSmAlertDestPriorityIndex      INTEGER,
        cpqSmAlertDestType               INTEGER,
        cpqSmAlertDestRetries            INTEGER,
        cpqSmAlertDestConnectFlags       INTEGER,
        cpqSmAlertDestPhoneNumber        DisplayString,
        cpqSmAlertDestTimeMask           OCTET STRING,
        cpqSmAlertDestPagerType          INTEGER,
        cpqSmAlertDestPagerId            DisplayString,
        cpqSmAlertDestPagerDisplayLength INTEGER
        }

    cpqSmAlertDestPriorityIndex OBJECT-TYPE
        SYNTAX  INTEGER (0..255)
        ACCESS  read-only
        STATUS  mandatory
        DESCRIPTION
            "This is a number that uniquely specifies this alert
            destination.  This number is also the priority of the alert
            destination.  When an alert occurs, alert destinations are tried
            in an order based on their priority (lowest number first).
	    The priority index is one based, meaning index one (1) 
	    is the highest priority index (and tried first), index two (2) 
	    is next, and so forth."
        ::= { cpqSmAlertDestEntry 1 }

    cpqSmAlertDestType OBJECT-TYPE
        SYNTAX  INTEGER {
            other(1),
            internalModemToSmf(161),
            internalModemToPager(162),
            internalModemToVoice(163),
            externalModemToSmf(164),
            externalModemToPager(165),
            externalDirectToSmf(166)
            }
        ACCESS  read-only
        STATUS  mandatory
        DESCRIPTION
            "The type of connection appropriate for the destination."
        ::= { cpqSmAlertDestEntry 2 }

    cpqSmAlertDestRetries OBJECT-TYPE
        SYNTAX  INTEGER  (0..31)
        ACCESS  read-only
        STATUS  mandatory
        DESCRIPTION
            "The number of retries for a successful connection that should be
            attempted to this alert destination."
        ::= { cpqSmAlertDestEntry 3 }

    cpqSmAlertDestConnectFlags OBJECT-TYPE
        SYNTAX  INTEGER {
            other(1),
            alertOnly(2),
            callbackOnly(3),
            alertAndCallback(4)
            }
        ACCESS  read-only
        STATUS  mandatory
        DESCRIPTION
            "The type(s) of communication that this destination supports."
        ::= { cpqSmAlertDestEntry 4 }

    cpqSmAlertDestPhoneNumber OBJECT-TYPE
        SYNTAX  DisplayString (SIZE (0..24))
        ACCESS  read-only
        STATUS  mandatory
        DESCRIPTION
            "The phone number for this destination.  This field is undefined
            if the alertDestType is externalDirectToSmf."
        ::= { cpqSmAlertDestEntry 5 }

    cpqSmAlertDestTimeMask OBJECT-TYPE
        SYNTAX  OCTET STRING (SIZE (21))
        ACCESS  read-only
        STATUS  mandatory
        DESCRIPTION
            "A set of bit flags specifying the times this is a valid
            destination.  Each bit specifies whether it this is a valid
            destination for a specific hour of the week.  The first bit
            is for the hour 12:00:01 am to 1:00:00 am on Monday.  Each bit
            thereafter specifies the validity of this destination for the
            next hour."
        ::= { cpqSmAlertDestEntry 6 }

    cpqSmAlertDestPagerType OBJECT-TYPE
        SYNTAX  INTEGER {
            other(1),
            numericOnly(2),
            alphanumeric(3)
            }
        ACCESS  read-only
        STATUS  mandatory
        DESCRIPTION
            "The type of pager at this destination.  This field is undefined
            if the alertDestType is internalModemToSmf, internalModemToVoice, 
            externalModemToSmf, or externalDirectToSmf."
        ::= { cpqSmAlertDestEntry 7 }

    cpqSmAlertDestPagerId OBJECT-TYPE
        SYNTAX  DisplayString (SIZE (0..15))
        ACCESS  read-only
        STATUS  mandatory
        DESCRIPTION
            "The pager ID assigned by the paging company to identify the
            pager.  This field is undefined if the alertDestType is
            internalModemToSmf, internalModemToVoice, externalModemToSmf,
            or externalDirectToSmf."
        ::= { cpqSmAlertDestEntry 8 }

    cpqSmAlertDestPagerDisplayLength OBJECT-TYPE
        SYNTAX  INTEGER  (0..80) 
        ACCESS  read-only
        STATUS  mandatory
        DESCRIPTION
            "The size of the pager display.  This field is undefined if the
            alertDestType is internalModemToSmf, internalModemToVoice,
            externalModemToSmf, or externalDirectToSmf."
        ::= { cpqSmAlertDestEntry 9 }

-- ****************************************************************************
--   Server Manager Trap Group
--   =========================
--
-- The compaq enterprise             (232)
--      cpqServerManager Group       (232.4)
--       cpqSmTrap Group             (232.4.3)
--
--      The cpqSmTrap group maintains information about the number of traps
--      issued from the cpqServerManager enterprise.  The cpqSmTrap group
--      also maintains a table of the last several traps issued.  This table
--      is intended to give a management application some recent status
--      information immediately upon accessing the agent.
--
--      Implementation of the cpqSmTrap group is optional for agents that
--      support the Compaq Server Manager MIB.
--
-- ****************************************************************************

    cpqSmTrapPkts OBJECT-TYPE
        SYNTAX  Counter
        ACCESS  read-only
        STATUS  mandatory
        DESCRIPTION
            "The total number of trap packets issued by the agent for the 
            cpqSmServerManager enterprise since the Server Manager SNMP
            agent was loaded."
        ::= { cpqSmTrap 1 }

    cpqSmTrapLogMaxSize OBJECT-TYPE
        SYNTAX  INTEGER (0..2147483647)
        ACCESS  read-only
        STATUS  mandatory
        DESCRIPTION
            "The maximum number of entries that will currently be kept in 
            the trap log.  If the maximum size has been reached and a new
            trap occurs the oldest trap will be removed."
        ::= { cpqSmTrap 2 }

-- ****************************************************************************
--   Server Manager Trap Log Table
--   =============================
--
-- The compaq enterprise             (232)
--      cpqServerManager Group       (232.4)
--       cpqSmTrap Group             (232.4.3)
--        cpqSmTrapLogTable          (232.4.3.3)
--
-- ****************************************************************************

    cpqSmTrapLogTable OBJECT-TYPE
        SYNTAX  SEQUENCE OF CpqSmTrapLogEntry
        ACCESS  not-accessible
        STATUS  mandatory
        DESCRIPTION
            "An ordered list of trap log entries (conceptually a queue).  The
            trap log entries will be kept in the order in which they were
            generated with the most recent trap at index 1 and the oldest
            trap entry at index trapLogMaxSize.  If the maximum number size
            has been reached and a new trap occurs the oldest trap will be
            removed when the new trap is added so the trapMaxLogSize is not
            exceeded."
        ::= { cpqSmTrap 3 }

    cpqSmTrapLogEntry OBJECT-TYPE
        SYNTAX  CpqSmTrapLogEntry
        ACCESS  not-accessible
        STATUS  mandatory
        DESCRIPTION
            "A description of a trap event."
        INDEX   { cpqSmTrapLogIndex }
        ::= { cpqSmTrapLogTable 1 }

    CpqSmTrapLogEntry ::= SEQUENCE {
        cpqSmTrapLogIndex        INTEGER,
        cpqSmTrapType            INTEGER,
        cpqSmTrapTime            OCTET STRING
    }

    cpqSmTrapLogIndex OBJECT-TYPE
        SYNTAX  INTEGER (0..2147483647)
        ACCESS  read-only
        STATUS  mandatory
        DESCRIPTION
            "The value of this object uniquely identifies this trapLogEntry
            at this time.  The most recent trap will have an index of 1 and
            the oldest trap will have an index of trapLogMaxSize.  Because of
            the queue-like nature of the trapLog this particular trap event's
            index will change as new traps are issued."
        ::= { cpqSmTrapLogEntry 1 }

    cpqSmTrapType OBJECT-TYPE
        SYNTAX  INTEGER {
            cpqSmBoardFailed(1),
            cpqSmBoardReset(2),
            cpqSmServerManagerAlert(3),
            cpqSmCommFailed(4),
            cpqSmBatteryFailed(5),
            cpqSmBoardTimeout(6),
            cpqSmAlertDestinationBlacklisted(7)
            }
        ACCESS  read-only
        STATUS  mandatory
        DESCRIPTION
            "The type of the trap event that this entry describes.  This
            number refers to an entry in a list of traps enumerating the
            possible traps the Server Manager agent may issue."
        ::= { cpqSmTrapLogEntry 2 }

    cpqSmTrapTime OBJECT-TYPE
        SYNTAX  OCTET STRING (SIZE (6))
        ACCESS  read-only
        STATUS  mandatory
        DESCRIPTION
            "The time of the trap event that this entry describes.  The time
            is given in year (first octet), month, day of month, hour,
            minute, second (last octet) order.  Each octet is a BCD number."
        ::= { cpqSmTrapLogEntry 3 }

-- ****************************************************************************
--   Server Manager Trap Definition
--   ==============================
--
--  Server Manager Trap Definitions
--  NOTE:  Server Manager Trap Definitions are based on the 
--         cpqServerManager enterprise.
--
--  Trap support in an SNMP agent implementation is optional.  An SNMP
--  agent implementation may support all, some, or none of the traps.
--
-- ****************************************************************************

    cpqSmBoardFailed TRAP-TYPE
        ENTERPRISE cpqServerManager
        DESCRIPTION
            "Server Manager board failure.
					   
             The Insight Agent has detected a failure of the Compaq Server 
             Manager/R board in the server."

              --#TYPE "Server Manager/R Board Failed"
              --#SUMMARY "Server Manager/R board failure detected."
              --#ARGUMENTS {}
              --#SEVERITY CRITICAL
              --#TIMEINDEX 99
              --#STATE   DEGRADED

        ::= 1
          
    cpqSmBoardReset TRAP-TYPE
        ENTERPRISE cpqServerManager
        DESCRIPTION
            "Server Manager board reset.

             The Insight Agent has detected a reset of the Server Manager/R
             board in the server."

              --#TYPE "Server Manager/R Board Reset"
              --#SUMMARY "Server Manager/R board has been reset."
              --#ARGUMENTS {}
              --#SEVERITY MINOR
              --#TIMEINDEX 99
              --#STATE   DEGRADED

        ::= 2

      cpqSmServerManagerAlert TRAP-TYPE
        ENTERPRISE cpqServerManager
        VARIABLES  { cpqSmMonItemCurVal , cpqSmObjectLabel, 
                     cpqSmMonItemLabel , cpqSmMonItemDataType ,
                     cpqSmMonItemSeverity , cpqSmMonItemLimit ,
                     cpqSmMonItemOptional , cpqSmMonItemLogicalOperator , 
        		     cpqSmMonItemTimeStamp }
        DESCRIPTION
            "Threshold exeeded on Server Manager monitored item.

             The Insight Agent has detected a monitored item on the Server 
             Manager board exceeding a threshold when alerting is
             enabled for the monitored item."

              --#TYPE "Server Manager/R Threshhold Exceeded"
              --#SUMMARY "The %s - %s = %d."
              --#ARGUMENTS {1,2,0}
              --#SEVERITY CRITICAL
              --#TIMEINDEX 99

        ::= 3

    cpqSmCommFailed TRAP-TYPE
        ENTERPRISE cpqServerManager
        DESCRIPTION
            "Server Manager asynchronous communications failure.

            The Insight Agent has detected a failure in the Server Manager 
            board's asynchronous communication system."

              --#TYPE "Async Comm Failure"
              --#SUMMARY "Async comm failure on Server Manager/R Board."
              --#ARGUMENTS {}
              --#SEVERITY CRITICAL
              --#TIMEINDEX 99
              --#STATE   DEGRADED

        ::= 4

    cpqSmBatteryFailed TRAP-TYPE
        ENTERPRISE cpqServerManager
        DESCRIPTION
            "Server Manager battery failure.

            The Insight Agent has detected a failure in the Server Manager 
            board's onboard battery."

              --#TYPE "Battery Failure"
              --#SUMMARY "Server Manager/R battery has failed."
              --#ARGUMENTS {}
              --#SEVERITY MAJOR
              --#TIMEINDEX 99
              --#STATE   DEGRADED

        ::= 5

    cpqSmBoardTimeout TRAP-TYPE
        ENTERPRISE cpqServerManager
        DESCRIPTION
            "Server Manager board time-out.

             The Insight Agent has detected a time-out of the Server
             Manager board as reported by the Server Manager Board driver."

              --#TYPE "Board Timeout"
              --#SUMMARY "Server Manager/R board is not responding."
              --#ARGUMENTS {}
              --#SEVERITY CRITICAL
              --#TIMEINDEX 99
              --#STATE   DEGRADED

        ::= 6

    cpqSmAlertDestinationBlacklisted TRAP-TYPE
	ENTERPRISE cpqServerManager
	VARIABLES  { cpqSmAlertDestType, cpqSmAlertDestPhoneNumber, 
                cpqSmAlertDestPagerId }
	DESCRIPTION
	    "Alert destination blacklisted.

             The Server Manager board modem has blacklisted an alert 
             destination phone number.  Once blacklisted, that alert 
             destination is no longer available for use as an alert 
             destination.  Blacklisting, which only occurs in 
             international modems, is a requirement imposed by certain 
             European countries on modems, to prevent a phone number 
             from being dialed multiple times without getting a connection.  
             The number of attempts required to have blacklisting occur,
	     vary from country to country.  Once an alert destination has 
	     been blacklisted, the only way to remove the blacklisted phone 
	     number is to remove power from the modem.  
	     On external modems this is a trival task.  When a blacklisting
	     occurs on the Server Manager board's internal modem the
	     task is slightly more difficult as the modem gets power 
	     from the Server Manager board.  
	     To remove power from the Server Manager board's internal modem,
	     the Server Manager board must be forced into Dormant Mode.
	     This is an operating mode, used to conserve battery life,
	     which is entered automatically if the board looses power.
	     To cause the board to enter Dormant Mode, the following
	     steps should be performed:
	       1) Disable alerting via CPQCAUI.NLM.
	       2) Disable async communication via CPQCAUI.NLM.
	       3) Down the server.
	       4) Exit to DOS (if applicable).
	       5) Shut power off to the computer.
	       6) Wait 5 minutes before restoring power.
	     Once the 5 minutes has expired, and power to the computer
	     has been restored, the modem will have flushed its
	     blacklist, and the board's alerting functions will work
	     as expected."

              --#TYPE "Alert Destination Blacklisted"
              --#SUMMARY "Phone# %s, Pager ID %s blacklisted."
              --#ARGUMENTS {1,2}
              --#SEVERITY MINOR
              --#TIMEINDEX 99
              --#STATE   DEGRADED

	::= 7

END
