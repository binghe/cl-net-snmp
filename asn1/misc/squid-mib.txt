SQUID-MIB  DEFINITIONS ::= BEGIN
--
-- $Id: squid-mib-06.my,v 1.12 2001/02/23 20:56:51 nreddy Exp $
--

IMPORTS
	enterprises, Unsigned32, TimeTicks, Gauge32, Counter32,
	MODULE-IDENTITY, OBJECT-TYPE
        	FROM SNMPv2-SMI

	DisplayString
        	FROM SNMPv2-TC;

nlanr OBJECT IDENTIFIER ::= { enterprises 3495 }

squid MODULE-IDENTITY
    LAST-UPDATED "9809220000Z"
    ORGANIZATION "National Laboratory for Applied Network Research"
    CONTACT-INFO
            "        Glenn Chisholm

             Postal: National Centre for Atmospheric Research (NCAR)
		     Room 36, SCD
		     PO Box 3000
                     Boulder, Colorado 80307  
                     US

                Tel: +1 303 497 1289
                Fax: +1 303 497 1818

             E-mail: glenn@ircache.net"
    DESCRIPTION
		"Squid MIB defined for the management of the squid
		proxy server. See http://squid.nlanr.net/."
	    
    REVISION      "9809220000Z"
    DESCRIPTION
		"Move to SMIv2. Prepare to split into proxy/squid."
    ::= { nlanr 1 }

--
-- OID Assignments
--

	cacheSystem	OBJECT IDENTIFIER ::= { squid 1 }
	cacheConfig  	OBJECT IDENTIFIER ::= { squid 2 }
	cachePerf	OBJECT IDENTIFIER ::= { squid 3 }
	cacheNetwork	OBJECT IDENTIFIER ::= { squid 4 } 
	cacheMesh	OBJECT IDENTIFIER ::= { squid 5 }


--
-- cacheSystem group
--

        cacheSysVMsize OBJECT-TYPE
	        SYNTAX Integer32
		MAX-ACCESS read-only
		STATUS current
		DESCRIPTION
			" Virtual Memory size in KB"
	::= { cacheSystem 1 }

	cacheSysStorage OBJECT-TYPE
		SYNTAX Integer32
		MAX-ACCESS read-only
                STATUS current
                DESCRIPTION
                        " Diskspace in KB"
        ::= { cacheSystem 2 }

	cacheUptime  OBJECT-TYPE
                SYNTAX TimeTicks
                MAX-ACCESS read-only
                STATUS current
                DESCRIPTION
                        " Number of timeticks since cache started "
	::= { cacheSystem 3 }

--
-- config group
--
-- Contains configuration information including peers etc.
--

	cacheAdmin OBJECT-TYPE
		SYNTAX DisplayString
		MAX-ACCESS read-only
                STATUS current
                DESCRIPTION
                        " Cache Administrator E-Mail address "
	::= { cacheConfig 1 }

        cacheSoftware OBJECT-TYPE
                SYNTAX DisplayString
                MAX-ACCESS read-only
                STATUS current
                DESCRIPTION
                        " Cache Software Name "
        ::= { cacheConfig 2 }

        cacheVersionId OBJECT-TYPE
                SYNTAX OCTET STRING (SIZE (0..32))
                MAX-ACCESS read-only
                STATUS current
                DESCRIPTION
                        " Cache Software Version "
        ::= { cacheConfig 3 }

	cacheLoggingFacility OBJECT-TYPE
		SYNTAX DisplayString
		MAX-ACCESS read-write
		STATUS current
		DESCRIPTION
			" Logging Facility. An informational string
			  indicating logging info like debug level, 
			  local/syslog/remote logging etc " 
	::= { cacheConfig 4 } 

-- cacheStorageConfig group

	cacheStorageConfig OBJECT IDENTIFIER ::= { cacheConfig 5 }

	cacheMemMaxSize OBJECT-TYPE
                SYNTAX Integer32
                MAX-ACCESS read-only
                STATUS current
                DESCRIPTION
                        " Cache Memory Maximum Size "
        ::= { cacheStorageConfig 1 }

	cacheMemHighWM OBJECT-TYPE
                SYNTAX Integer32
                MAX-ACCESS read-only
                STATUS current
                DESCRIPTION
                        " Cache Memory High Water Mark "
        ::= { cacheStorageConfig 2 }

        cacheMemLowWM OBJECT-TYPE
                SYNTAX Integer32
                MAX-ACCESS read-only
                STATUS current
                DESCRIPTION
                        " Cache Memory Low Water Mark "
        ::= { cacheStorageConfig 3 }

        cacheSwapMaxSize OBJECT-TYPE
                SYNTAX Integer32
                MAX-ACCESS read-only
                STATUS current
                DESCRIPTION
                        " Cache Swap Maximum Size "
        ::= { cacheStorageConfig 4 }

        cacheSwapHighWM OBJECT-TYPE
                SYNTAX Integer32
                MAX-ACCESS read-only
                STATUS current
                DESCRIPTION
                        " Cache Swap High Water Mark "
        ::= { cacheStorageConfig 5 }

        cacheSwapLowWM OBJECT-TYPE
                SYNTAX Integer32
                MAX-ACCESS read-only
                STATUS current
                DESCRIPTION
                        " Cache Swap Low Water Mark "
        ::= { cacheStorageConfig 6 }

-- end of  cacheStorageConfig group

--
-- performance group { squid 3 }
--

	cacheSysPerf    OBJECT IDENTIFIER ::= { cachePerf 1 } 
        cacheProtoStats OBJECT IDENTIFIER ::= { cachePerf 2 }

	--
	-- cacheSysPerf 
	--

        cacheSysPageFaults OBJECT-TYPE
                SYNTAX Counter32
                MAX-ACCESS read-only
                STATUS current
                DESCRIPTION
                        " Number of system page faults "
        ::= { cacheSysPerf 1 }

        cacheSysNumReads OBJECT-TYPE
                SYNTAX Counter32
                MAX-ACCESS not-accessible
                STATUS current 
                DESCRIPTION
                        " Number of Reads " 
       	::= { cacheSysPerf 2 }

        cacheSysDefReads OBJECT-TYPE
                SYNTAX Counter32
                MAX-ACCESS not-accessible
                STATUS current
		DESCRIPTION
			" see cachemgr "
       	::= { cacheSysPerf 3 }

	cacheMemUsage OBJECT-TYPE
		SYNTAX Integer32
		MAX-ACCESS read-only
		STATUS 	current
		DESCRIPTION
			" Amount of system memory allocated by the cache"
	::= { cacheSysPerf 4 } 

	cacheCpuUsage OBJECT-TYPE
		SYNTAX Integer32
		MAX-ACCESS read-only
                STATUS  current
                DESCRIPTION
                        " Amount of cpu seconds consumed"
	::= { cacheSysPerf 5 }

	cacheMaxResSize OBJECT-TYPE
                SYNTAX Integer32
                MAX-ACCESS read-only
                STATUS  current
                DESCRIPTION
                        " Maximum Resident Size"
        ::= { cacheSysPerf 6 }

	cacheNumObjCount OBJECT-TYPE
                SYNTAX Counter32                 
		MAX-ACCESS read-only
                STATUS  current
                DESCRIPTION
                        " Number of objects "
        ::= { cacheSysPerf 7 }

        cacheCurrentLRUExpiration OBJECT-TYPE
                SYNTAX TimeTicks
                MAX-ACCESS read-only
                STATUS current
                DESCRIPTION " "
        ::= { cacheSysPerf 8 }

        cacheCurrentUnlinkRequests OBJECT-TYPE
                SYNTAX Counter32
                MAX-ACCESS read-only
                STATUS current
                DESCRIPTION " "
        ::= { cacheSysPerf 9 }

        cacheCurrentUnusedFileDescrCount OBJECT-TYPE
                SYNTAX Gauge32
                MAX-ACCESS read-only
                STATUS current
                DESCRIPTION " "
        ::= { cacheSysPerf 10 }

	cacheCurrentReservedFileDescrCount  OBJECT-TYPE
                SYNTAX Gauge32
                MAX-ACCESS read-only
                STATUS current
                DESCRIPTION " "
        ::= { cacheSysPerf 11 }

	--
	-- cacheProtoStats
	--

		-- cacheProtoAggregateStats
		--

	cacheProtoAggregateStats OBJECT IDENTIFIER ::= { cacheProtoStats 1 }


	cacheClientProtoHttpRequests  OBJECT-TYPE
                SYNTAX Counter32
                MAX-ACCESS read-only
                STATUS current
                DESCRIPTION " "
        ::= { cacheProtoAggregateStats 1 }

        cacheHttpHits OBJECT-TYPE
                SYNTAX Counter32
                MAX-ACCESS read-only
                STATUS current
                DESCRIPTION " "
        ::= { cacheProtoAggregateStats 2 }

        cacheHttpErrors OBJECT-TYPE
                SYNTAX Counter32
                MAX-ACCESS read-only
                STATUS current
                DESCRIPTION " "
        ::= { cacheProtoAggregateStats 3 }

        cacheHttpInKb OBJECT-TYPE
                SYNTAX Counter32
                MAX-ACCESS read-only
                STATUS current
                DESCRIPTION " "
        ::= { cacheProtoAggregateStats 4 }

        cacheHttpOutKb OBJECT-TYPE
                SYNTAX Counter32
                MAX-ACCESS read-only
                STATUS current
                DESCRIPTION " "
        ::= { cacheProtoAggregateStats 5 }

	cacheIcpPktsSent OBJECT-TYPE
                SYNTAX Counter32
                MAX-ACCESS read-only
                STATUS current
                DESCRIPTION " "
        ::= { cacheProtoAggregateStats 6 }

	cacheIcpPktsRecv OBJECT-TYPE
                SYNTAX Counter32
                MAX-ACCESS read-only
                STATUS current
                DESCRIPTION " "
        ::= { cacheProtoAggregateStats 7 }

        cacheIcpKbSent OBJECT-TYPE
                SYNTAX Counter32
                MAX-ACCESS read-only
                STATUS current
                DESCRIPTION " "
        ::= { cacheProtoAggregateStats 8 }

        cacheIcpKbRecv OBJECT-TYPE
                SYNTAX Counter32
                MAX-ACCESS read-only
                STATUS current
                DESCRIPTION " "
        ::= { cacheProtoAggregateStats 9 }

        cacheServerRequests OBJECT-TYPE
                SYNTAX Integer32
                MAX-ACCESS read-only
                STATUS current
                DESCRIPTION " "
        ::= { cacheProtoAggregateStats 10 }

        cacheServerErrors OBJECT-TYPE
                SYNTAX Integer32
                MAX-ACCESS read-only
                STATUS current
                DESCRIPTION " "
        ::= { cacheProtoAggregateStats 11 }

	cacheServerInKb OBJECT-TYPE
                SYNTAX Counter32
                MAX-ACCESS read-only
                STATUS current
                DESCRIPTION " "
        ::= { cacheProtoAggregateStats 12 }

        cacheServerOutKb OBJECT-TYPE
                SYNTAX Counter32
                MAX-ACCESS read-only
                STATUS current
                DESCRIPTION " "
        ::= { cacheProtoAggregateStats 13 }

	cacheCurrentSwapSize OBJECT-TYPE
                SYNTAX Counter32
                MAX-ACCESS read-only
                STATUS current
                DESCRIPTION " "
        ::= { cacheProtoAggregateStats 14 }

       cacheClients OBJECT-TYPE
                SYNTAX Counter32
                MAX-ACCESS read-only
                STATUS current
                DESCRIPTION " "
        ::= { cacheProtoAggregateStats 15 }

	--
	-- cacheProtoMedianSvcStats group
	-- 
	-- This is a table, indexed by the interval we want statistics for
	-- Example: cacheDnsSvcTime.10 gives 10-min medians for Dns Service Time.

	cacheMedianSvcTable OBJECT-TYPE
                SYNTAX SEQUENCE OF CacheMedianSvcEntry
                MAX-ACCESS not-accessible
--                MAX-ACCESS read-only
                STATUS current
                DESCRIPTION " "
	::= { cacheProtoStats 2 }

        cacheMedianSvcEntry OBJECT-TYPE
                SYNTAX CacheMedianSvcEntry
                MAX-ACCESS not-accessible
                STATUS current
                DESCRIPTION 
                        " An entry in cacheMedianSvcTable " 
                INDEX   { cacheMedianTime }
        ::= { cacheMedianSvcTable 1 }

        CacheMedianSvcEntry ::= SEQUENCE {
		cacheMedianTime		Integer32,
		cacheHttpAllSvcTime 	Integer32,
		cacheHttpMissSvcTime 	Integer32,	
		cacheHttpNmSvcTime 	Integer32,
		cacheHttpHitSvcTime 	Integer32,
		cacheIcpQuerySvcTime 	Integer32,
		cacheIcpReplySvcTime 	Integer32,
		cacheDnsSvcTime		Integer32,
        	cacheRequestHitRatio 	Integer32,
        	cacheRequestByteRatio 	Integer32
	}

	cacheMedianTime OBJECT-TYPE
                SYNTAX Integer32
                MAX-ACCESS read-only
                STATUS current
                DESCRIPTION " "
        ::= { cacheMedianSvcEntry 1 }

	cacheHttpAllSvcTime OBJECT-TYPE
                SYNTAX Integer32
                MAX-ACCESS read-only
                STATUS current
                DESCRIPTION " "
        ::= { cacheMedianSvcEntry 2 } 

	cacheHttpMissSvcTime OBJECT-TYPE
                SYNTAX Integer32
                MAX-ACCESS read-only
                STATUS current
                DESCRIPTION " "
        ::= { cacheMedianSvcEntry 3 } 

	cacheHttpNmSvcTime OBJECT-TYPE
                SYNTAX Integer32
                MAX-ACCESS read-only
                STATUS current
                DESCRIPTION " "
        ::= { cacheMedianSvcEntry 4 } 

	cacheHttpHitSvcTime OBJECT-TYPE
                SYNTAX Integer32
                MAX-ACCESS read-only
                STATUS current
                DESCRIPTION " "
        ::= { cacheMedianSvcEntry 5 } 

	cacheIcpQuerySvcTime OBJECT-TYPE
                SYNTAX Integer32
                MAX-ACCESS read-only
                STATUS current
                DESCRIPTION " "
        ::= { cacheMedianSvcEntry 6 } 

	cacheIcpReplySvcTime OBJECT-TYPE
                SYNTAX Integer32
                MAX-ACCESS read-only
                STATUS current
                DESCRIPTION " "
        ::= { cacheMedianSvcEntry 7 } 

	cacheDnsSvcTime OBJECT-TYPE
                SYNTAX Integer32
                MAX-ACCESS read-only
                STATUS current
                DESCRIPTION " "
        ::= { cacheMedianSvcEntry 8 } 

        cacheRequestHitRatio OBJECT-TYPE
                SYNTAX Integer32
                MAX-ACCESS read-only
                STATUS current
                DESCRIPTION " "
        ::= { cacheMedianSvcEntry 9 }

        cacheRequestByteRatio OBJECT-TYPE
                SYNTAX Integer32
                MAX-ACCESS read-only
                STATUS current
                DESCRIPTION " "
        ::= { cacheMedianSvcEntry 10 }

--
-- cacheNetwork group
--
-- This material is probably best suited elsewhere, however for now it
-- will reside here until the both the Proxy and Squid MIBs are implimented.
--

	cacheIpCache	OBJECT IDENTIFIER ::= { cacheNetwork 1 }
	cacheFqdnCache	OBJECT IDENTIFIER ::= { cacheNetwork 2 } 
	cacheDns	OBJECT IDENTIFIER ::= { cacheNetwork 3 }

--
-- cacheIpCache
--

	cacheEntries OBJECT-TYPE
                SYNTAX Gauge32
                MAX-ACCESS read-only
                STATUS current
                DESCRIPTION " "
        ::= { cacheIpCache 1 } 

	cacheRequests OBJECT-TYPE
                SYNTAX Counter32
                MAX-ACCESS read-only
                STATUS current
                DESCRIPTION " "
        ::= { cacheIpCache 2 } 

	cacheHits OBJECT-TYPE
                SYNTAX Counter32
                MAX-ACCESS read-only
                STATUS current
                DESCRIPTION " "
        ::= { cacheIpCache 3 } 

	cachePendingHits OBJECT-TYPE
                SYNTAX Gauge32
                MAX-ACCESS read-only
                STATUS current
                DESCRIPTION " "
        ::= { cacheIpCache 4 } 

	cacheNegativeHits OBJECT-TYPE
                SYNTAX Counter32
                MAX-ACCESS read-only
                STATUS current
                DESCRIPTION " "
        ::= { cacheIpCache 5 } 

	cacheMisses OBJECT-TYPE
                SYNTAX Counter32
                MAX-ACCESS read-only
                STATUS current
                DESCRIPTION " "
        ::= { cacheIpCache 6 } 

	cacheBlockingGetHostByName OBJECT-TYPE
                SYNTAX Counter32
                MAX-ACCESS read-only
                STATUS current
                DESCRIPTION " "
        ::= { cacheIpCache 7 } 

	cacheAttemptReleaseLockedEntries OBJECT-TYPE
                SYNTAX Counter32
                MAX-ACCESS read-only
                STATUS current
                DESCRIPTION " "
        ::= { cacheIpCache 8 } 

--
-- cacheFqdnCache
--

	cacheFqdnEntries OBJECT-TYPE
                SYNTAX Gauge32
                MAX-ACCESS read-only
                STATUS current
                DESCRIPTION " "
        ::= { cacheFqdnCache 1 } 

	cacheFqdnRequests OBJECT-TYPE
                SYNTAX Counter32
                MAX-ACCESS read-only
                STATUS current
                DESCRIPTION " "
        ::= { cacheFqdnCache 2 } 

	cacheFqdnHits OBJECT-TYPE
                SYNTAX Counter32
                MAX-ACCESS read-only
                STATUS current
                DESCRIPTION " "
        ::= { cacheFqdnCache 3 } 

	cacheFqdnPendingHits OBJECT-TYPE
                SYNTAX Gauge32
                MAX-ACCESS read-only
                STATUS current
                DESCRIPTION " "
        ::= { cacheFqdnCache 4 } 

	cacheFqdnNegativeHits OBJECT-TYPE
                SYNTAX Counter32
                MAX-ACCESS read-only
                STATUS current
                DESCRIPTION " "
        ::= { cacheFqdnCache 5 } 

	cacheFqdnMisses OBJECT-TYPE
                SYNTAX Counter32
                MAX-ACCESS read-only
                STATUS current
                DESCRIPTION " "
        ::= { cacheFqdnCache 6 } 

	cacheFqdnBlockingGetHostByAddr OBJECT-TYPE
                SYNTAX Counter32
                MAX-ACCESS read-only
                STATUS current
                DESCRIPTION " "
        ::= { cacheFqdnCache 7 } 

--
--	cacheDNS 
--

	cacheDnsRequests OBJECT-TYPE
                SYNTAX Counter32
                MAX-ACCESS read-only
                STATUS current
                DESCRIPTION " "
        ::= { cacheDns 1 } 

	cacheDnsReplies OBJECT-TYPE
                SYNTAX Counter32
                MAX-ACCESS read-only
                STATUS current
                DESCRIPTION " "
        ::= { cacheDns 2 } 

	cacheDnsNumberServers OBJECT-TYPE
                SYNTAX Counter32
                MAX-ACCESS read-only
                STATUS current
                DESCRIPTION " "
        ::= { cacheDns 3 } 
	
--
-- cacheMesh group
--

	cachePeerTable OBJECT-TYPE
		SYNTAX SEQUENCE OF CachePeerEntry
--		MAX-ACCESS read-only
                MAX-ACCESS not-accessible
		STATUS current
		DESCRIPTION
			" This table contains an enumeration of
			  the peer caches, complete with info "
        ::= { cacheMesh 1 }

	cachePeerEntry OBJECT-TYPE
		SYNTAX CachePeerEntry
		MAX-ACCESS not-accessible
		STATUS current
		DESCRIPTION 
			" An entry in cachePeerTable " 
		INDEX 	{ cachePeerAddr }
	::= { cachePeerTable 1 }

	CachePeerEntry ::= SEQUENCE {
	  cachePeerName		DisplayString,
	  cachePeerAddr  	IpAddress,
	  cachePeerPortHttp 	Integer32 (1..65535),
	  cachePeerPortIcp	Integer32 (1..65535),
	  cachePeerType 	Integer32,
	  cachePeerState	Integer32,
	  cachePeerPingsSent	Counter32,
	  cachePeerPingsAcked	Counter32,
	  cachePeerFetches	Counter32,
	  cachePeerRtt		Integer32,
	  cachePeerIgnored	Counter32,
	  cachePeerKeepAlSent	Counter32,
	  cachePeerKeepAlRecv	Counter32
	}

	cachePeerName OBJECT-TYPE
		SYNTAX DisplayString
		MAX-ACCESS read-only
		STATUS current
		DESCRIPTION 
			  " The FQDN name or internal alias for the
		      	    peer cache"
	::= { cachePeerEntry 1 } 

	cachePeerAddr OBJECT-TYPE
                SYNTAX IpAddress
                MAX-ACCESS read-only
                STATUS current
		DESCRIPTION 
			" The IP Address of the peer cache "
        ::= { cachePeerEntry 2 }

	cachePeerPortHttp OBJECT-TYPE
                SYNTAX Integer32
                MAX-ACCESS read-only
                STATUS current
		DESCRIPTION 
			" The port the peer listens for HTTP requests "
        ::= { cachePeerEntry 3 }

	cachePeerPortIcp OBJECT-TYPE
                SYNTAX Integer32
                MAX-ACCESS read-only
                STATUS current
		DESCRIPTION 
			" The port the peer listens for ICP requests 
			  should be 0 if not configured to send ICP requests "
        ::= { cachePeerEntry 4 }

	cachePeerType OBJECT-TYPE
                SYNTAX INTEGER {
				none(0), 
				sibling(1), 
                                parent(2), 
				multicast(3)
                                }
                MAX-ACCESS not-accessible
                STATUS current
                DESCRIPTION 
                        " Peer Type "
	::= { cachePeerEntry 5 } 

	cachePeerState OBJECT-TYPE
                SYNTAX INTEGER { 
				down(0), 
				up(1)
				}
                MAX-ACCESS read-only
                STATUS current
		DESCRIPTION 
			" The operational state of this peer "
        ::= { cachePeerEntry 6 }

        cachePeerPingsSent OBJECT-TYPE
                SYNTAX Counter32
                MAX-ACCESS read-only
                STATUS current
		DESCRIPTION 
			" Number of pings sent to peer "
        ::= { cachePeerEntry 7 }

        cachePeerPingsAcked OBJECT-TYPE
                SYNTAX Counter32
                MAX-ACCESS read-only
                STATUS current
		DESCRIPTION 
			" Number of pings received from peer "
        ::= {  cachePeerEntry 8 }

        cachePeerFetches OBJECT-TYPE
                SYNTAX Counter32
                MAX-ACCESS read-only
                STATUS current
		DESCRIPTION 
			" Number of times this peer was selected  "
        ::= { cachePeerEntry 9 }

        cachePeerRtt OBJECT-TYPE
                SYNTAX Integer32
                MAX-ACCESS read-only
                STATUS current
		DESCRIPTION 
			" Last known round-trip time to the peer (in ms) "
        ::= { cachePeerEntry 10 }

        cachePeerIgnored OBJECT-TYPE
                SYNTAX Counter32
                MAX-ACCESS read-only
                STATUS current
		DESCRIPTION 
			" How many times this peer was ignored "
        ::= { cachePeerEntry 11 }

        cachePeerKeepAlSent OBJECT-TYPE
                SYNTAX Counter32
                MAX-ACCESS read-only
                STATUS current
		DESCRIPTION 
			" Number of keepalives sent "
        ::= { cachePeerEntry 12 }

        cachePeerKeepAlRecv OBJECT-TYPE
                SYNTAX Counter32
                MAX-ACCESS read-only
                STATUS current
		DESCRIPTION 
			" Number of keepalives received "
        ::= { cachePeerEntry 13 }

---
--- Table of cache's clients, with statistics. Children caches can be identified
--- by non-zero number of ICP requests (unless browsers start using ICP).
---	

        cacheClientTable OBJECT-TYPE
           SYNTAX  SEQUENCE OF CacheClientEntry
           MAX-ACCESS not-accessible
--           MAX-ACCESS  read-only
           STATUS  current
           DESCRIPTION
                    "A list of cache client entries."
       	::= { cacheMesh 2 }

	cacheClientEntry OBJECT-TYPE
           SYNTAX CacheClientEntry
           MAX-ACCESS  not-accessible
           STATUS  current
           DESCRIPTION
                    "An entry in cacheClientTable"
	   INDEX { cacheClientAddr }
	::= { cacheClientTable 1 }

	CacheClientEntry ::= SEQUENCE {
               	cacheClientAddr 	IpAddress,
               	cacheClientHttpRequests	Counter32,
               	cacheClientHttpKb 	Counter32,
               	cacheClientHttpHits 	Counter32,
               	cacheClientHTTPHitKb	Counter32,
		cacheClientIcpRequests	Counter32,
		cacheClientIcpKb 	Counter32,
               	cacheClientIcpHits 	Counter32,
               	cacheClientIcpHitKb	Counter32
	}

	cacheClientAddr OBJECT-TYPE
                SYNTAX IpAddress
                MAX-ACCESS read-only
                STATUS current
           	DESCRIPTION
                    "The client's IP address "
        ::= { cacheClientEntry 1 }

	cacheClientHttpRequests OBJECT-TYPE
                SYNTAX Counter32
                MAX-ACCESS read-only
                STATUS current
           	DESCRIPTION
                    " Number of HTTP requests received from client "
        ::= { cacheClientEntry 2 }

	cacheClientHttpKb OBJECT-TYPE
                SYNTAX Counter32
                MAX-ACCESS read-only
                STATUS current
           	DESCRIPTION
                    " Amount of total HTTP traffic to this client  "
        ::= { cacheClientEntry 3 }

        cacheClientHttpHits OBJECT-TYPE
                SYNTAX Counter32
                MAX-ACCESS read-only
                STATUS current
           	DESCRIPTION
                    " Number of hits in response to this client's HTTP requests "
        ::= { cacheClientEntry 4 }

        cacheClientHTTPHitKb OBJECT-TYPE
                SYNTAX Counter32
                MAX-ACCESS read-only
                STATUS current
           	DESCRIPTION
                    " Amount of HTTP hit traffic in KB "
        ::= { cacheClientEntry 5 }

	cacheClientIcpRequests OBJECT-TYPE
                SYNTAX Counter32
                MAX-ACCESS read-only
                STATUS current
           	DESCRIPTION
                    " Number of ICP requests received from client "
        ::= { cacheClientEntry 6 }

	cacheClientIcpKb OBJECT-TYPE
                SYNTAX Counter32
                MAX-ACCESS read-only
                STATUS current
           	DESCRIPTION
                    " Amount of total ICP traffic to this client (child) "
        ::= { cacheClientEntry 7 }

        cacheClientIcpHits OBJECT-TYPE
                SYNTAX Counter32
                MAX-ACCESS read-only
                STATUS current
           	DESCRIPTION
                    " Number of hits in response to this client's ICP requests "
        ::= { cacheClientEntry 8 }

        cacheClientIcpHitKb OBJECT-TYPE
                SYNTAX Counter32
                MAX-ACCESS read-only
                STATUS current
           	DESCRIPTION
                    " Amount of ICP hit traffic in KB "
        ::= { cacheClientEntry 9 }

	-- end of cacheClientTable
  
 
    -- end of cacheMesh group

-- end of SQUID-MIB
--
END
