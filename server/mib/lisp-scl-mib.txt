-- -*- Mode: asn1 -*-
-- $Id$

LISP-SCL-MIB DEFINITIONS ::= BEGIN

IMPORTS
    MODULE-IDENTITY, OBJECT-TYPE, OBJECT-IDENTITY,
    NOTIFICATION-TYPE, enterprises
        FROM SNMPv2-SMI

    common-lisp FROM LISP-MIB;

scl MODULE-IDENTITY
    LAST-UPDATED "200807290000Z" -- 29 July 2008
    ORGANIZATION
           "The cl-net-snmp Project
	    http://common-lisp.net/projects/cl-net-snmp"
    CONTACT-INFO
           "Chun Tian (binghe)

            Email: <binghe.lisp@gmail.com>

            Send comments to
              <cl-net-snmp-general@lists.sourceforge.net>"
    DESCRIPTION
           "The MIB module for Scieneer CL"

    REVISION "200811150000Z" -- 15 November 2008
    DESCRIPTION
           "The initial revision of this MIB module."

    ::= { common-lisp 10 }

END
